PDU-MIB DEFINITIONS ::= BEGIN
IMPORTS
enterprises, Counter,
TimeTicks, Gauge FROM RFC1155-SMI
OBJECT-TYPE FROM RFC-1212

sysUpTime, DisplayString FROM RFC1213-MIB
TRAP-TYPE FROM RFC-1215;
pdu OBJECT IDENTIFIER ::= { enterprises 42578 }
pdu1 OBJECT IDENTIFIER ::= { pdu 1 }
pdu2 OBJECT IDENTIFIER ::= { pdu 2 }
pdu3 OBJECT IDENTIFIER ::= { pdu 3 }
pdu4 OBJECT IDENTIFIER ::= { pdu 4 }
pdu5 OBJECT IDENTIFIER ::= { pdu 5 }
pdu6 OBJECT IDENTIFIER ::= { pdu 6 }
pdu7 OBJECT IDENTIFIER ::= { pdu 7 }
pdu8 OBJECT IDENTIFIER ::= { pdu 8 }
pdu9 OBJECT IDENTIFIER ::= { pdu 9 }
pdu10 OBJECT IDENTIFIER ::= { pdu 10 }
pdu11 OBJECT IDENTIFIER ::= { pdu 11 }
baseinfo1 OBJECT IDENTIFIER ::= { pdu1 1 }

cascadeAlarmPDU1 OBJECT-TYPE
SYNTAX INTEGER (0..3)
ACCESS read-only
STATUS optional
DESCRIPTION
        " "
::= { baseinfo1 1 }

deviceNamePDU1 OBJECT-TYPE
SYNTAX DisplayString (SIZE (32))
ACCESS read-write
STATUS optional
DESCRIPTION
        " "
::= { baseinfo1 2 }

outletNumberPDU1 OBJECT-TYPE
SYNTAX INTEGER (0..36)
ACCESS read-only
STATUS optional
DESCRIPTION
        " "
::= { baseinfo1 3 }

temphum1WarnStatPDU1 OBJECT-TYPE
SYNTAX INTEGER (0..127)
ACCESS read-only
STATUS optional
DESCRIPTION
        " "
::= { baseinfo1 4 }

temphum2WarnStatPDU1 OBJECT-TYPE
SYNTAX INTEGER (0..127)
ACCESS read-only
STATUS optional
DESCRIPTION
        " "
::= { baseinfo1 5 }

input1WarnStatPDU1 OBJECT-TYPE
SYNTAX INTEGER (0..1)
ACCESS read-only
STATUS optional
DESCRIPTION
        " "
::= { baseinfo1 6 }

input2WarnStatPDU1 OBJECT-TYPE
SYNTAX INTEGER (0..1)
ACCESS read-only
STATUS optional
DESCRIPTION
        " "
::= { baseinfo1 7 }

input3WarnStatPDU1 OBJECT-TYPE
SYNTAX INTEGER (0..1)
ACCESS read-only
STATUS optional
DESCRIPTION
        " "
::= { baseinfo1 8 }

input4WarnStatPDU1 OBJECT-TYPE
SYNTAX INTEGER (0..1)
ACCESS read-only
STATUS optional
DESCRIPTION
        " "
::= { baseinfo1 9 }

currentL1WarnStatPDU1 OBJECT-TYPE
SYNTAX INTEGER (0..127)
ACCESS read-only
STATUS optional
DESCRIPTION
        " "
::= { baseinfo1 10 }

currentL2WarnStatPDU1 OBJECT-TYPE
SYNTAX INTEGER (0..127)
ACCESS read-only
STATUS optional
DESCRIPTION
        " "
::= { baseinfo1 11 }

currentL3WarnStatPDU1 OBJECT-TYPE
SYNTAX INTEGER (0..127)
ACCESS read-only
STATUS optional
DESCRIPTION
        " "
::= { baseinfo1 12 }

voltageL1WarnStatPDU1 OBJECT-TYPE
SYNTAX INTEGER (0..127)
ACCESS read-only
STATUS optional
DESCRIPTION
        " "
::= { baseinfo1 13 }

voltageL2WarnStatPDU1 OBJECT-TYPE
SYNTAX INTEGER (0..127)
ACCESS read-only
STATUS optional
DESCRIPTION
        " "
::= { baseinfo1 14 }

voltageL3WarnStatPDU1 OBJECT-TYPE
SYNTAX INTEGER (0..127)
ACCESS read-only
STATUS optional
DESCRIPTION
        " "
::= { baseinfo1 15 }

outlet1WarnStatPDU1 OBJECT-TYPE
SYNTAX INTEGER (0..127)
ACCESS read-only
STATUS optional
DESCRIPTION
        " "
::= { baseinfo1 16 }

outlet2WarnStatPDU1 OBJECT-TYPE
SYNTAX INTEGER (0..127)
ACCESS read-only
STATUS optional
DESCRIPTION
        " "
::= { baseinfo1 17 }

outlet3WarnStatPDU1 OBJECT-TYPE
SYNTAX INTEGER (0..127)
ACCESS read-only
STATUS optional
DESCRIPTION
        " "
::= { baseinfo1 18 }

outlet4WarnStatPDU1 OBJECT-TYPE
SYNTAX INTEGER (0..127)
ACCESS read-only
STATUS optional
DESCRIPTION
        " "
::= { baseinfo1 19 }

outlet5WarnStatPDU1 OBJECT-TYPE
SYNTAX INTEGER (0..127)
ACCESS read-only
STATUS optional
DESCRIPTION
        " "
::= { baseinfo1 20 }

outlet6WarnStatPDU1 OBJECT-TYPE
SYNTAX INTEGER (0..127)
ACCESS read-only
STATUS optional
DESCRIPTION
        " "
::= { baseinfo1 21 }

outlet7WarnStatPDU1 OBJECT-TYPE
SYNTAX INTEGER (0..127)
ACCESS read-only
STATUS optional
DESCRIPTION
        " "
::= { baseinfo1 22 }

outlet8WarnStatPDU1 OBJECT-TYPE
SYNTAX INTEGER (0..127)
ACCESS read-only
STATUS optional
DESCRIPTION
        " "
::= { baseinfo1 23 }

outlet9WarnStatPDU1 OBJECT-TYPE
SYNTAX INTEGER (0..127)
ACCESS read-only
STATUS optional
DESCRIPTION
        " "
::= { baseinfo1 24 }

outlet10WarnStatPDU1 OBJECT-TYPE
SYNTAX INTEGER (0..127)
ACCESS read-only
STATUS optional
DESCRIPTION
        " "
::= { baseinfo1 25 }

outlet11WarnStatPDU1 OBJECT-TYPE
SYNTAX INTEGER (0..127)
ACCESS read-only
STATUS optional
DESCRIPTION
        " "
::= { baseinfo1 26 }

outlet12WarnStatPDU1 OBJECT-TYPE
SYNTAX INTEGER (0..127)
ACCESS read-only
STATUS optional
DESCRIPTION
        " "
::= { baseinfo1 27 }

outlet13WarnStatPDU1 OBJECT-TYPE
SYNTAX INTEGER (0..127)
ACCESS read-only
STATUS optional
DESCRIPTION
        " "
::= { baseinfo1 28 }

outlet14WarnStatPDU1 OBJECT-TYPE
SYNTAX INTEGER (0..127)
ACCESS read-only
STATUS optional
DESCRIPTION
        " "
::= { baseinfo1 29 }

outlet15WarnStatPDU1 OBJECT-TYPE
SYNTAX INTEGER (0..127)
ACCESS read-only
STATUS optional
DESCRIPTION
        " "
::= { baseinfo1 30 }

outlet16WarnStatPDU1 OBJECT-TYPE
SYNTAX INTEGER (0..127)
ACCESS read-only
STATUS optional
DESCRIPTION
        " "
::= { baseinfo1 31 }

outlet17WarnStatPDU1 OBJECT-TYPE
SYNTAX INTEGER (0..127)
ACCESS read-only
STATUS optional
DESCRIPTION
        " "
::= { baseinfo1 32 }

outlet18WarnStatPDU1 OBJECT-TYPE
SYNTAX INTEGER (0..127)
ACCESS read-only
STATUS optional
DESCRIPTION
        " "
::= { baseinfo1 33 }

outlet19WarnStatPDU1 OBJECT-TYPE
SYNTAX INTEGER (0..127)
ACCESS read-only
STATUS optional
DESCRIPTION
        " "
::= { baseinfo1 34 }

outlet20WarnStatPDU1 OBJECT-TYPE
SYNTAX INTEGER (0..127)
ACCESS read-only
STATUS optional
DESCRIPTION
        " "
::= { baseinfo1 35 }

outlet21WarnStatPDU1 OBJECT-TYPE
SYNTAX INTEGER (0..127)
ACCESS read-only
STATUS optional
DESCRIPTION
        " "
::= { baseinfo1 36 }

outlet22WarnStatPDU1 OBJECT-TYPE
SYNTAX INTEGER (0..127)
ACCESS read-only
STATUS optional
DESCRIPTION
        " "
::= { baseinfo1 37 }

outlet23WarnStatPDU1 OBJECT-TYPE
SYNTAX INTEGER (0..127)
ACCESS read-only
STATUS optional
DESCRIPTION
        " "
::= { baseinfo1 38 }

outlet24WarnStatPDU1 OBJECT-TYPE
SYNTAX INTEGER (0..127)
ACCESS read-only
STATUS optional
DESCRIPTION
        " "
::= { baseinfo1 39 }

outlet25WarnStatPDU1 OBJECT-TYPE
SYNTAX INTEGER (0..127)
ACCESS read-only
STATUS optional
DESCRIPTION
        " "
::= { baseinfo1 40 }

outlet26WarnStatPDU1 OBJECT-TYPE
SYNTAX INTEGER (0..127)
ACCESS read-only
STATUS optional
DESCRIPTION
        " "
::= { baseinfo1 41 }

outlet27WarnStatPDU1 OBJECT-TYPE
SYNTAX INTEGER (0..127)
ACCESS read-only
STATUS optional
DESCRIPTION
        " "
::= { baseinfo1 42 }

outlet28WarnStatPDU1 OBJECT-TYPE
SYNTAX INTEGER (0..127)
ACCESS read-only
STATUS optional
DESCRIPTION
        " "
::= { baseinfo1 43 }

outlet29WarnStatPDU1 OBJECT-TYPE
SYNTAX INTEGER (0..127)
ACCESS read-only
STATUS optional
DESCRIPTION
        " "
::= { baseinfo1 44 }

outlet30WarnStatPDU1 OBJECT-TYPE
SYNTAX INTEGER (0..127)
ACCESS read-only
STATUS optional
DESCRIPTION
        " "
::= { baseinfo1 45 }

outlet31WarnStatPDU1 OBJECT-TYPE
SYNTAX INTEGER (0..127)
ACCESS read-only
STATUS optional
DESCRIPTION
        " "
::= { baseinfo1 46 }

outlet32WarnStatPDU1 OBJECT-TYPE
SYNTAX INTEGER (0..127)
ACCESS read-only
STATUS optional
DESCRIPTION
        " "
::= { baseinfo1 47 }

outlet33WarnStatPDU1 OBJECT-TYPE
SYNTAX INTEGER (0..127)
ACCESS read-only
STATUS optional
DESCRIPTION
        " "
::= { baseinfo1 48 }

outlet34WarnStatPDU1 OBJECT-TYPE
SYNTAX INTEGER (0..127)
ACCESS read-only
STATUS optional
DESCRIPTION
        " "
::= { baseinfo1 49 }

outlet35WarnStatPDU1 OBJECT-TYPE
SYNTAX INTEGER (0..127)
ACCESS read-only
STATUS optional
DESCRIPTION
        " "
::= { baseinfo1 50 }

outlet36WarnStatPDU1 OBJECT-TYPE
SYNTAX INTEGER (0..127)
ACCESS read-only
STATUS optional
DESCRIPTION
        " "
::= { baseinfo1 51 }

input1 OBJECT IDENTIFIER ::= { pdu1 2 }

currentL1PDU1 OBJECT-TYPE
SYNTAX INTEGER (0..65535)
ACCESS read-only
STATUS optional
DESCRIPTION
        " "
::= { input1 1 }

voltageL1PDU1 OBJECT-TYPE
SYNTAX INTEGER (0..65535)
ACCESS read-only
STATUS optional
DESCRIPTION
        " "
::= { input1 2 }

powerL1PDU1 OBJECT-TYPE
SYNTAX INTEGER (0..65535)
ACCESS read-only
STATUS optional
DESCRIPTION
        " "
::= { input1 3 }

pfL1PDU1 OBJECT-TYPE
SYNTAX INTEGER (0..65535)
ACCESS read-only
STATUS optional
DESCRIPTION
        " "
::= { input1 4 }

energyL1PDU1 OBJECT-TYPE
SYNTAX INTEGER (0..65535)
ACCESS read-only
STATUS optional
DESCRIPTION
        " "
::= { input1 5 }

currentL2PDU1 OBJECT-TYPE
SYNTAX INTEGER (0..65535)
ACCESS read-only
STATUS optional
DESCRIPTION
        " "
::= { input1 6 }

voltageL2PDU1 OBJECT-TYPE
SYNTAX INTEGER (0..65535)
ACCESS read-only
STATUS optional
DESCRIPTION
        " "
::= { input1 7 }

powerL2PDU1 OBJECT-TYPE
SYNTAX INTEGER (0..65535)
ACCESS read-only
STATUS optional
DESCRIPTION
        " "
::= { input1 8 }

pfL2PDU1 OBJECT-TYPE
SYNTAX INTEGER (0..65535)
ACCESS read-only
STATUS optional
DESCRIPTION
        " "
::= { input1 9 }

energyL2PDU1 OBJECT-TYPE
SYNTAX INTEGER (0..65535)
ACCESS read-only
STATUS optional
DESCRIPTION
        " "
::= { input1 10 }

currentL3PDU1 OBJECT-TYPE
SYNTAX INTEGER (0..65535)
ACCESS read-only
STATUS optional
DESCRIPTION
        " "
::= { input1 11 }

voltageL3PDU1 OBJECT-TYPE
SYNTAX INTEGER (0..65535)
ACCESS read-only
STATUS optional
DESCRIPTION
        " "
::= { input1 12 }

powerL3PDU1 OBJECT-TYPE
SYNTAX INTEGER (0..65535)
ACCESS read-only
STATUS optional
DESCRIPTION
        " "
::= { input1 13 }

pfL3PDU1 OBJECT-TYPE
SYNTAX INTEGER (0..65535)
ACCESS read-only
STATUS optional
DESCRIPTION
        " "
::= { input1 14 }

energyL3PDU1 OBJECT-TYPE
SYNTAX INTEGER (0..65535)
ACCESS read-only
STATUS optional
DESCRIPTION
        " "
::= { input1 15 }

outletinfo1 OBJECT IDENTIFIER ::= { pdu1 3 }

outlet1PDU1 OBJECT IDENTIFIER ::= { outletinfo1 1 }

outlet2PDU1 OBJECT IDENTIFIER ::= { outletinfo1 2 }

outlet3PDU1 OBJECT IDENTIFIER ::= { outletinfo1 3 }

outlet4PDU1 OBJECT IDENTIFIER ::= { outletinfo1 4 }

outlet5PDU1 OBJECT IDENTIFIER ::= { outletinfo1 5 }

outlet6PDU1 OBJECT IDENTIFIER ::= { outletinfo1 6 }

outlet7PDU1 OBJECT IDENTIFIER ::= { outletinfo1 7 }

outlet8PDU1 OBJECT IDENTIFIER ::= { outletinfo1 8 }

outlet9PDU1 OBJECT IDENTIFIER ::= { outletinfo1 9 }

outlet10PDU1 OBJECT IDENTIFIER ::= { outletinfo1 10 }

outlet11PDU1 OBJECT IDENTIFIER ::= { outletinfo1 11 }

outlet12PDU1 OBJECT IDENTIFIER ::= { outletinfo1 12 }

outlet13PDU1 OBJECT IDENTIFIER ::= { outletinfo1 13 }

outlet14PDU1 OBJECT IDENTIFIER ::= { outletinfo1 14 }

outlet15PDU1 OBJECT IDENTIFIER ::= { outletinfo1 15 }

outlet16PDU1 OBJECT IDENTIFIER ::= { outletinfo1 16 }

outlet17PDU1 OBJECT IDENTIFIER ::= { outletinfo1 17 }

outlet18PDU1 OBJECT IDENTIFIER ::= { outletinfo1 18 }

outlet19PDU1 OBJECT IDENTIFIER ::= { outletinfo1 19 }

outlet20PDU1 OBJECT IDENTIFIER ::= { outletinfo1 20 }

outlet21PDU1 OBJECT IDENTIFIER ::= { outletinfo1 21 }

outlet22PDU1 OBJECT IDENTIFIER ::= { outletinfo1 22 }

outlet23PDU1 OBJECT IDENTIFIER ::= { outletinfo1 23 }

outlet24PDU1 OBJECT IDENTIFIER ::= { outletinfo1 24 }

outlet25PDU1 OBJECT IDENTIFIER ::= { outletinfo1 25 }

outlet26PDU1 OBJECT IDENTIFIER ::= { outletinfo1 26 }

outlet27PDU1 OBJECT IDENTIFIER ::= { outletinfo1 27 }

outlet28PDU1 OBJECT IDENTIFIER ::= { outletinfo1 28 }

outlet29PDU1 OBJECT IDENTIFIER ::= { outletinfo1 29 }

outlet30PDU1 OBJECT IDENTIFIER ::= { outletinfo1 30 }

outlet31PDU1 OBJECT IDENTIFIER ::= { outletinfo1 31 }

outlet32PDU1 OBJECT IDENTIFIER ::= { outletinfo1 32 }

outlet33PDU1 OBJECT IDENTIFIER ::= { outletinfo1 33 }

outlet34PDU1 OBJECT IDENTIFIER ::= { outletinfo1 34 }

outlet35PDU1 OBJECT IDENTIFIER ::= { outletinfo1 35 }

outlet36PDU1 OBJECT IDENTIFIER ::= { outletinfo1 36 }

switch1PDU1 OBJECT-TYPE
SYNTAX INTEGER (0..3)
ACCESS read-write
STATUS optional
DESCRIPTION
        " "
::= { outlet1PDU1 1 }

voltage1PDU1 OBJECT-TYPE
SYNTAX INTEGER (0..65535)
ACCESS read-only
STATUS optional
DESCRIPTION
        " "
::= { outlet1PDU1 2 }

current1PDU1 OBJECT-TYPE
SYNTAX INTEGER (0..65535)
ACCESS read-only
STATUS optional
DESCRIPTION
        " "
::= { outlet1PDU1 3 }

power1PDU1 OBJECT-TYPE
SYNTAX INTEGER (0..65535)
ACCESS read-only
STATUS optional
DESCRIPTION
        " "
::= { outlet1PDU1 4 }

pf1PDU1 OBJECT-TYPE
SYNTAX INTEGER (0..65535)
ACCESS read-only
STATUS optional
DESCRIPTION
        " "
::= { outlet1PDU1 5 }

energy1PDU1 OBJECT-TYPE
SYNTAX INTEGER (0..65535)
ACCESS read-only
STATUS optional
DESCRIPTION
        " "
::= { outlet1PDU1 6 }

switch2PDU1 OBJECT-TYPE
SYNTAX INTEGER (0..3)
ACCESS read-write
STATUS optional
DESCRIPTION
        " "
::= { outlet2PDU1 1 }

voltage2PDU1 OBJECT-TYPE
SYNTAX INTEGER (0..65535)
ACCESS read-only
STATUS optional
DESCRIPTION
        " "
::= { outlet2PDU1 2 }

current2PDU1 OBJECT-TYPE
SYNTAX INTEGER (0..65535)
ACCESS read-only
STATUS optional
DESCRIPTION
        " "
::= { outlet2PDU1 3 }

power2PDU1 OBJECT-TYPE
SYNTAX INTEGER (0..65535)
ACCESS read-only
STATUS optional
DESCRIPTION
        " "
::= { outlet2PDU1 4 }

pf2PDU1 OBJECT-TYPE
SYNTAX INTEGER (0..65535)
ACCESS read-only
STATUS optional
DESCRIPTION
        " "
::= { outlet2PDU1 5 }

energy2PDU1 OBJECT-TYPE
SYNTAX INTEGER (0..65535)
ACCESS read-only
STATUS optional
DESCRIPTION
        " "
::= { outlet2PDU1 6 }

switch3PDU1 OBJECT-TYPE
SYNTAX INTEGER (0..3)
ACCESS read-write
STATUS optional
DESCRIPTION
        " "
::= { outlet3PDU1 1 }

voltage3PDU1 OBJECT-TYPE
SYNTAX INTEGER (0..65535)
ACCESS read-only
STATUS optional
DESCRIPTION
        " "
::= { outlet3PDU1 2 }

current3PDU1 OBJECT-TYPE
SYNTAX INTEGER (0..65535)
ACCESS read-only
STATUS optional
DESCRIPTION
        " "
::= { outlet3PDU1 3 }

power3PDU1 OBJECT-TYPE
SYNTAX INTEGER (0..65535)
ACCESS read-only
STATUS optional
DESCRIPTION
        " "
::= { outlet3PDU1 4 }

pf3PDU1 OBJECT-TYPE
SYNTAX INTEGER (0..65535)
ACCESS read-only
STATUS optional
DESCRIPTION
        " "
::= { outlet3PDU1 5 }

energy3PDU1 OBJECT-TYPE
SYNTAX INTEGER (0..65535)
ACCESS read-only
STATUS optional
DESCRIPTION
        " "
::= { outlet3PDU1 6 }

switch4PDU1 OBJECT-TYPE
SYNTAX INTEGER (0..3)
ACCESS read-write
STATUS optional
DESCRIPTION
        " "
::= { outlet4PDU1 1 }

voltage4PDU1 OBJECT-TYPE
SYNTAX INTEGER (0..65535)
ACCESS read-only
STATUS optional
DESCRIPTION
        " "
::= { outlet4PDU1 2 }

current4PDU1 OBJECT-TYPE
SYNTAX INTEGER (0..65535)
ACCESS read-only
STATUS optional
DESCRIPTION
        " "
::= { outlet4PDU1 3 }

power4PDU1 OBJECT-TYPE
SYNTAX INTEGER (0..65535)
ACCESS read-only
STATUS optional
DESCRIPTION
        " "
::= { outlet4PDU1 4 }

pf4PDU1 OBJECT-TYPE
SYNTAX INTEGER (0..65535)
ACCESS read-only
STATUS optional
DESCRIPTION
        " "
::= { outlet4PDU1 5 }

energy4PDU1 OBJECT-TYPE
SYNTAX INTEGER (0..65535)
ACCESS read-only
STATUS optional
DESCRIPTION
        " "
::= { outlet4PDU1 6 }

switch5PDU1 OBJECT-TYPE
SYNTAX INTEGER (0..3)
ACCESS read-write
STATUS optional
DESCRIPTION
        " "
::= { outlet5PDU1 1 }

voltage5PDU1 OBJECT-TYPE
SYNTAX INTEGER (0..65535)
ACCESS read-only
STATUS optional
DESCRIPTION
        " "
::= { outlet5PDU1 2 }

current5PDU1 OBJECT-TYPE
SYNTAX INTEGER (0..65535)
ACCESS read-only
STATUS optional
DESCRIPTION
        " "
::= { outlet5PDU1 3 }

power5PDU1 OBJECT-TYPE
SYNTAX INTEGER (0..65535)
ACCESS read-only
STATUS optional
DESCRIPTION
        " "
::= { outlet5PDU1 4 }

pf5PDU1 OBJECT-TYPE
SYNTAX INTEGER (0..65535)
ACCESS read-only
STATUS optional
DESCRIPTION
        " "
::= { outlet5PDU1 5 }

energy5PDU1 OBJECT-TYPE
SYNTAX INTEGER (0..65535)
ACCESS read-only
STATUS optional
DESCRIPTION
        " "
::= { outlet5PDU1 6 }

switch6PDU1 OBJECT-TYPE
SYNTAX INTEGER (0..3)
ACCESS read-write
STATUS optional
DESCRIPTION
        " "
::= { outlet6PDU1 1 }

voltage6PDU1 OBJECT-TYPE
SYNTAX INTEGER (0..65535)
ACCESS read-only
STATUS optional
DESCRIPTION
        " "
::= { outlet6PDU1 2 }

current6PDU1 OBJECT-TYPE
SYNTAX INTEGER (0..65535)
ACCESS read-only
STATUS optional
DESCRIPTION
        " "
::= { outlet6PDU1 3 }

power6PDU1 OBJECT-TYPE
SYNTAX INTEGER (0..65535)
ACCESS read-only
STATUS optional
DESCRIPTION
        " "
::= { outlet6PDU1 4 }

pf6PDU1 OBJECT-TYPE
SYNTAX INTEGER (0..65535)
ACCESS read-only
STATUS optional
DESCRIPTION
        " "
::= { outlet6PDU1 5 }

energy6PDU1 OBJECT-TYPE
SYNTAX INTEGER (0..65535)
ACCESS read-only
STATUS optional
DESCRIPTION
        " "
::= { outlet6PDU1 6 }

switch7PDU1 OBJECT-TYPE
SYNTAX INTEGER (0..3)
ACCESS read-write
STATUS optional
DESCRIPTION
        " "
::= { outlet7PDU1 1 }

voltage7PDU1 OBJECT-TYPE
SYNTAX INTEGER (0..65535)
ACCESS read-only
STATUS optional
DESCRIPTION
        " "
::= { outlet7PDU1 2 }

current7PDU1 OBJECT-TYPE
SYNTAX INTEGER (0..65535)
ACCESS read-only
STATUS optional
DESCRIPTION
        " "
::= { outlet7PDU1 3 }

power7PDU1 OBJECT-TYPE
SYNTAX INTEGER (0..65535)
ACCESS read-only
STATUS optional
DESCRIPTION
        " "
::= { outlet7PDU1 4 }

pf7PDU1 OBJECT-TYPE
SYNTAX INTEGER (0..65535)
ACCESS read-only
STATUS optional
DESCRIPTION
        " "
::= { outlet7PDU1 5 }

energy7PDU1 OBJECT-TYPE
SYNTAX INTEGER (0..65535)
ACCESS read-only
STATUS optional
DESCRIPTION
        " "
::= { outlet7PDU1 6 }

switch8PDU1 OBJECT-TYPE
SYNTAX INTEGER (0..3)
ACCESS read-write
STATUS optional
DESCRIPTION
        " "
::= { outlet8PDU1 1 }

voltage8PDU1 OBJECT-TYPE
SYNTAX INTEGER (0..65535)
ACCESS read-only
STATUS optional
DESCRIPTION
        " "
::= { outlet8PDU1 2 }

current8PDU1 OBJECT-TYPE
SYNTAX INTEGER (0..65535)
ACCESS read-only
STATUS optional
DESCRIPTION
        " "
::= { outlet8PDU1 3 }

power8PDU1 OBJECT-TYPE
SYNTAX INTEGER (0..65535)
ACCESS read-only
STATUS optional
DESCRIPTION
        " "
::= { outlet8PDU1 4 }

pf8PDU1 OBJECT-TYPE
SYNTAX INTEGER (0..65535)
ACCESS read-only
STATUS optional
DESCRIPTION
        " "
::= { outlet8PDU1 5 }

energy8PDU1 OBJECT-TYPE
SYNTAX INTEGER (0..65535)
ACCESS read-only
STATUS optional
DESCRIPTION
        " "
::= { outlet8PDU1 6 }

switch9PDU1 OBJECT-TYPE
SYNTAX INTEGER (0..3)
ACCESS read-write
STATUS optional
DESCRIPTION
        " "
::= { outlet9PDU1 1 }

voltage9PDU1 OBJECT-TYPE
SYNTAX INTEGER (0..65535)
ACCESS read-only
STATUS optional
DESCRIPTION
        " "
::= { outlet9PDU1 2 }

current9PDU1 OBJECT-TYPE
SYNTAX INTEGER (0..65535)
ACCESS read-only
STATUS optional
DESCRIPTION
        " "
::= { outlet9PDU1 3 }

power9PDU1 OBJECT-TYPE
SYNTAX INTEGER (0..65535)
ACCESS read-only
STATUS optional
DESCRIPTION
        " "
::= { outlet9PDU1 4 }

pf9PDU1 OBJECT-TYPE
SYNTAX INTEGER (0..65535)
ACCESS read-only
STATUS optional
DESCRIPTION
        " "
::= { outlet9PDU1 5 }

energy9PDU1 OBJECT-TYPE
SYNTAX INTEGER (0..65535)
ACCESS read-only
STATUS optional
DESCRIPTION
        " "
::= { outlet9PDU1 6 }

switch10PDU1 OBJECT-TYPE
SYNTAX INTEGER (0..3)
ACCESS read-write
STATUS optional
DESCRIPTION
        " "
::= { outlet10PDU1 1 }

voltage10PDU1 OBJECT-TYPE
SYNTAX INTEGER (0..65535)
ACCESS read-only
STATUS optional
DESCRIPTION
        " "
::= { outlet10PDU1 2 }

current10PDU1 OBJECT-TYPE
SYNTAX INTEGER (0..65535)
ACCESS read-only
STATUS optional
DESCRIPTION
        " "
::= { outlet10PDU1 3 }

power10PDU1 OBJECT-TYPE
SYNTAX INTEGER (0..65535)
ACCESS read-only
STATUS optional
DESCRIPTION
        " "
::= { outlet10PDU1 4 }

pf10PDU1 OBJECT-TYPE
SYNTAX INTEGER (0..65535)
ACCESS read-only
STATUS optional
DESCRIPTION
        " "
::= { outlet10PDU1 5 }

energy10PDU1 OBJECT-TYPE
SYNTAX INTEGER (0..65535)
ACCESS read-only
STATUS optional
DESCRIPTION
        " "
::= { outlet10PDU1 6 }

switch11PDU1 OBJECT-TYPE
SYNTAX INTEGER (0..3)
ACCESS read-write
STATUS optional
DESCRIPTION
        " "
::= { outlet11PDU1 1 }

voltage11PDU1 OBJECT-TYPE
SYNTAX INTEGER (0..65535)
ACCESS read-only
STATUS optional
DESCRIPTION
        " "
::= { outlet11PDU1 2 }

current11PDU1 OBJECT-TYPE
SYNTAX INTEGER (0..65535)
ACCESS read-only
STATUS optional
DESCRIPTION
        " "
::= { outlet11PDU1 3 }

power11PDU1 OBJECT-TYPE
SYNTAX INTEGER (0..65535)
ACCESS read-only
STATUS optional
DESCRIPTION
        " "
::= { outlet11PDU1 4 }

pf11PDU1 OBJECT-TYPE
SYNTAX INTEGER (0..65535)
ACCESS read-only
STATUS optional
DESCRIPTION
        " "
::= { outlet11PDU1 5 }

energy11PDU1 OBJECT-TYPE
SYNTAX INTEGER (0..65535)
ACCESS read-only
STATUS optional
DESCRIPTION
        " "
::= { outlet11PDU1 6 }

switch12PDU1 OBJECT-TYPE
SYNTAX INTEGER (0..3)
ACCESS read-write
STATUS optional
DESCRIPTION
        " "
::= { outlet12PDU1 1 }

voltage12PDU1 OBJECT-TYPE
SYNTAX INTEGER (0..65535)
ACCESS read-only
STATUS optional
DESCRIPTION
        " "
::= { outlet12PDU1 2 }

current12PDU1 OBJECT-TYPE
SYNTAX INTEGER (0..65535)
ACCESS read-only
STATUS optional
DESCRIPTION
        " "
::= { outlet12PDU1 3 }

power12PDU1 OBJECT-TYPE
SYNTAX INTEGER (0..65535)
ACCESS read-only
STATUS optional
DESCRIPTION
        " "
::= { outlet12PDU1 4 }

pf12PDU1 OBJECT-TYPE
SYNTAX INTEGER (0..65535)
ACCESS read-only
STATUS optional
DESCRIPTION
        " "
::= { outlet12PDU1 5 }

energy12PDU1 OBJECT-TYPE
SYNTAX INTEGER (0..65535)
ACCESS read-only
STATUS optional
DESCRIPTION
        " "
::= { outlet12PDU1 6 }

switch13PDU1 OBJECT-TYPE
SYNTAX INTEGER (0..3)
ACCESS read-write
STATUS optional
DESCRIPTION
        " "
::= { outlet13PDU1 1 }

voltage13PDU1 OBJECT-TYPE
SYNTAX INTEGER (0..65535)
ACCESS read-only
STATUS optional
DESCRIPTION
        " "
::= { outlet13PDU1 2 }

current13PDU1 OBJECT-TYPE
SYNTAX INTEGER (0..65535)
ACCESS read-only
STATUS optional
DESCRIPTION
        " "
::= { outlet13PDU1 3 }

power13PDU1 OBJECT-TYPE
SYNTAX INTEGER (0..65535)
ACCESS read-only
STATUS optional
DESCRIPTION
        " "
::= { outlet13PDU1 4 }

pf13PDU1 OBJECT-TYPE
SYNTAX INTEGER (0..65535)
ACCESS read-only
STATUS optional
DESCRIPTION
        " "
::= { outlet13PDU1 5 }

energy13PDU1 OBJECT-TYPE
SYNTAX INTEGER (0..65535)
ACCESS read-only
STATUS optional
DESCRIPTION
        " "
::= { outlet13PDU1 6 }

switch14PDU1 OBJECT-TYPE
SYNTAX INTEGER (0..3)
ACCESS read-write
STATUS optional
DESCRIPTION
        " "
::= { outlet14PDU1 1 }

voltage14PDU1 OBJECT-TYPE
SYNTAX INTEGER (0..65535)
ACCESS read-only
STATUS optional
DESCRIPTION
        " "
::= { outlet14PDU1 2 }

current14PDU1 OBJECT-TYPE
SYNTAX INTEGER (0..65535)
ACCESS read-only
STATUS optional
DESCRIPTION
        " "
::= { outlet14PDU1 3 }

power14PDU1 OBJECT-TYPE
SYNTAX INTEGER (0..65535)
ACCESS read-only
STATUS optional
DESCRIPTION
        " "
::= { outlet14PDU1 4 }

pf14PDU1 OBJECT-TYPE
SYNTAX INTEGER (0..65535)
ACCESS read-only
STATUS optional
DESCRIPTION
        " "
::= { outlet14PDU1 5 }

energy14PDU1 OBJECT-TYPE
SYNTAX INTEGER (0..65535)
ACCESS read-only
STATUS optional
DESCRIPTION
        " "
::= { outlet14PDU1 6 }

switch15PDU1 OBJECT-TYPE
SYNTAX INTEGER (0..3)
ACCESS read-write
STATUS optional
DESCRIPTION
        " "
::= { outlet15PDU1 1 }

voltage15PDU1 OBJECT-TYPE
SYNTAX INTEGER (0..65535)
ACCESS read-only
STATUS optional
DESCRIPTION
        " "
::= { outlet15PDU1 2 }

current15PDU1 OBJECT-TYPE
SYNTAX INTEGER (0..65535)
ACCESS read-only
STATUS optional
DESCRIPTION
        " "
::= { outlet15PDU1 3 }

power15PDU1 OBJECT-TYPE
SYNTAX INTEGER (0..65535)
ACCESS read-only
STATUS optional
DESCRIPTION
        " "
::= { outlet15PDU1 4 }

pf15PDU1 OBJECT-TYPE
SYNTAX INTEGER (0..65535)
ACCESS read-only
STATUS optional
DESCRIPTION
        " "
::= { outlet15PDU1 5 }

energy15PDU1 OBJECT-TYPE
SYNTAX INTEGER (0..65535)
ACCESS read-only
STATUS optional
DESCRIPTION
        " "
::= { outlet15PDU1 6 }

switch16PDU1 OBJECT-TYPE
SYNTAX INTEGER (0..3)
ACCESS read-write
STATUS optional
DESCRIPTION
        " "
::= { outlet16PDU1 1 }

voltage16PDU1 OBJECT-TYPE
SYNTAX INTEGER (0..65535)
ACCESS read-only
STATUS optional
DESCRIPTION
        " "
::= { outlet16PDU1 2 }

current16PDU1 OBJECT-TYPE
SYNTAX INTEGER (0..65535)
ACCESS read-only
STATUS optional
DESCRIPTION
        " "
::= { outlet16PDU1 3 }

power16PDU1 OBJECT-TYPE
SYNTAX INTEGER (0..65535)
ACCESS read-only
STATUS optional
DESCRIPTION
        " "
::= { outlet16PDU1 4 }

pf16PDU1 OBJECT-TYPE
SYNTAX INTEGER (0..65535)
ACCESS read-only
STATUS optional
DESCRIPTION
        " "
::= { outlet16PDU1 5 }

energy16PDU1 OBJECT-TYPE
SYNTAX INTEGER (0..65535)
ACCESS read-only
STATUS optional
DESCRIPTION
        " "
::= { outlet16PDU1 6 }

switch17PDU1 OBJECT-TYPE
SYNTAX INTEGER (0..3)
ACCESS read-write
STATUS optional
DESCRIPTION
        " "
::= { outlet17PDU1 1 }

voltage17PDU1 OBJECT-TYPE
SYNTAX INTEGER (0..65535)
ACCESS read-only
STATUS optional
DESCRIPTION
        " "
::= { outlet17PDU1 2 }

current17PDU1 OBJECT-TYPE
SYNTAX INTEGER (0..65535)
ACCESS read-only
STATUS optional
DESCRIPTION
        " "
::= { outlet17PDU1 3 }

power17PDU1 OBJECT-TYPE
SYNTAX INTEGER (0..65535)
ACCESS read-only
STATUS optional
DESCRIPTION
        " "
::= { outlet17PDU1 4 }

pf17PDU1 OBJECT-TYPE
SYNTAX INTEGER (0..65535)
ACCESS read-only
STATUS optional
DESCRIPTION
        " "
::= { outlet17PDU1 5 }

energy17PDU1 OBJECT-TYPE
SYNTAX INTEGER (0..65535)
ACCESS read-only
STATUS optional
DESCRIPTION
        " "
::= { outlet17PDU1 6 }

switch18PDU1 OBJECT-TYPE
SYNTAX INTEGER (0..3)
ACCESS read-write
STATUS optional
DESCRIPTION
        " "
::= { outlet18PDU1 1 }

voltage18PDU1 OBJECT-TYPE
SYNTAX INTEGER (0..65535)
ACCESS read-only
STATUS optional
DESCRIPTION
        " "
::= { outlet18PDU1 2 }

current18PDU1 OBJECT-TYPE
SYNTAX INTEGER (0..65535)
ACCESS read-only
STATUS optional
DESCRIPTION
        " "
::= { outlet18PDU1 3 }

power18PDU1 OBJECT-TYPE
SYNTAX INTEGER (0..65535)
ACCESS read-only
STATUS optional
DESCRIPTION
        " "
::= { outlet18PDU1 4 }

pf18PDU1 OBJECT-TYPE
SYNTAX INTEGER (0..65535)
ACCESS read-only
STATUS optional
DESCRIPTION
        " "
::= { outlet18PDU1 5 }

energy18PDU1 OBJECT-TYPE
SYNTAX INTEGER (0..65535)
ACCESS read-only
STATUS optional
DESCRIPTION
        " "
::= { outlet18PDU1 6 }

switch19PDU1 OBJECT-TYPE
SYNTAX INTEGER (0..3)
ACCESS read-write
STATUS optional
DESCRIPTION
        " "
::= { outlet19PDU1 1 }

voltage19PDU1 OBJECT-TYPE
SYNTAX INTEGER (0..65535)
ACCESS read-only
STATUS optional
DESCRIPTION
        " "
::= { outlet19PDU1 2 }

current19PDU1 OBJECT-TYPE
SYNTAX INTEGER (0..65535)
ACCESS read-only
STATUS optional
DESCRIPTION
        " "
::= { outlet19PDU1 3 }

power19PDU1 OBJECT-TYPE
SYNTAX INTEGER (0..65535)
ACCESS read-only
STATUS optional
DESCRIPTION
        " "
::= { outlet19PDU1 4 }

pf19PDU1 OBJECT-TYPE
SYNTAX INTEGER (0..65535)
ACCESS read-only
STATUS optional
DESCRIPTION
        " "
::= { outlet19PDU1 5 }

energy19PDU1 OBJECT-TYPE
SYNTAX INTEGER (0..65535)
ACCESS read-only
STATUS optional
DESCRIPTION
        " "
::= { outlet19PDU1 6 }

switch20PDU1 OBJECT-TYPE
SYNTAX INTEGER (0..3)
ACCESS read-write
STATUS optional
DESCRIPTION
        " "
::= { outlet20PDU1 1 }

voltage20PDU1 OBJECT-TYPE
SYNTAX INTEGER (0..65535)
ACCESS read-only
STATUS optional
DESCRIPTION
        " "
::= { outlet20PDU1 2 }

current20PDU1 OBJECT-TYPE
SYNTAX INTEGER (0..65535)
ACCESS read-only
STATUS optional
DESCRIPTION
        " "
::= { outlet20PDU1 3 }

power20PDU1 OBJECT-TYPE
SYNTAX INTEGER (0..65535)
ACCESS read-only
STATUS optional
DESCRIPTION
        " "
::= { outlet20PDU1 4 }

pf20PDU1 OBJECT-TYPE
SYNTAX INTEGER (0..65535)
ACCESS read-only
STATUS optional
DESCRIPTION
        " "
::= { outlet20PDU1 5 }

energy20PDU1 OBJECT-TYPE
SYNTAX INTEGER (0..65535)
ACCESS read-only
STATUS optional
DESCRIPTION
        " "
::= { outlet20PDU1 6 }

switch21PDU1 OBJECT-TYPE
SYNTAX INTEGER (0..3)
ACCESS read-write
STATUS optional
DESCRIPTION
        " "
::= { outlet21PDU1 1 }

voltage21PDU1 OBJECT-TYPE
SYNTAX INTEGER (0..65535)
ACCESS read-only
STATUS optional
DESCRIPTION
        " "
::= { outlet21PDU1 2 }

current21PDU1 OBJECT-TYPE
SYNTAX INTEGER (0..65535)
ACCESS read-only
STATUS optional
DESCRIPTION
        " "
::= { outlet21PDU1 3 }

power21PDU1 OBJECT-TYPE
SYNTAX INTEGER (0..65535)
ACCESS read-only
STATUS optional
DESCRIPTION
        " "
::= { outlet21PDU1 4 }

pf21PDU1 OBJECT-TYPE
SYNTAX INTEGER (0..65535)
ACCESS read-only
STATUS optional
DESCRIPTION
        " "
::= { outlet21PDU1 5 }

energy21PDU1 OBJECT-TYPE
SYNTAX INTEGER (0..65535)
ACCESS read-only
STATUS optional
DESCRIPTION
        " "
::= { outlet21PDU1 6 }

switch22PDU1 OBJECT-TYPE
SYNTAX INTEGER (0..3)
ACCESS read-write
STATUS optional
DESCRIPTION
        " "
::= { outlet22PDU1 1 }

voltage22PDU1 OBJECT-TYPE
SYNTAX INTEGER (0..65535)
ACCESS read-only
STATUS optional
DESCRIPTION
        " "
::= { outlet22PDU1 2 }

current22PDU1 OBJECT-TYPE
SYNTAX INTEGER (0..65535)
ACCESS read-only
STATUS optional
DESCRIPTION
        " "
::= { outlet22PDU1 3 }

power22PDU1 OBJECT-TYPE
SYNTAX INTEGER (0..65535)
ACCESS read-only
STATUS optional
DESCRIPTION
        " "
::= { outlet22PDU1 4 }

pf22PDU1 OBJECT-TYPE
SYNTAX INTEGER (0..65535)
ACCESS read-only
STATUS optional
DESCRIPTION
        " "
::= { outlet22PDU1 5 }

energy22PDU1 OBJECT-TYPE
SYNTAX INTEGER (0..65535)
ACCESS read-only
STATUS optional
DESCRIPTION
        " "
::= { outlet22PDU1 6 }

switch23PDU1 OBJECT-TYPE
SYNTAX INTEGER (0..3)
ACCESS read-write
STATUS optional
DESCRIPTION
        " "
::= { outlet23PDU1 1 }

voltage23PDU1 OBJECT-TYPE
SYNTAX INTEGER (0..65535)
ACCESS read-only
STATUS optional
DESCRIPTION
        " "
::= { outlet23PDU1 2 }

current23PDU1 OBJECT-TYPE
SYNTAX INTEGER (0..65535)
ACCESS read-only
STATUS optional
DESCRIPTION
        " "
::= { outlet23PDU1 3 }

power23PDU1 OBJECT-TYPE
SYNTAX INTEGER (0..65535)
ACCESS read-only
STATUS optional
DESCRIPTION
        " "
::= { outlet23PDU1 4 }

pf23PDU1 OBJECT-TYPE
SYNTAX INTEGER (0..65535)
ACCESS read-only
STATUS optional
DESCRIPTION
        " "
::= { outlet23PDU1 5 }

energy23PDU1 OBJECT-TYPE
SYNTAX INTEGER (0..65535)
ACCESS read-only
STATUS optional
DESCRIPTION
        " "
::= { outlet23PDU1 6 }

switch24PDU1 OBJECT-TYPE
SYNTAX INTEGER (0..3)
ACCESS read-write
STATUS optional
DESCRIPTION
        " "
::= { outlet24PDU1 1 }

voltage24PDU1 OBJECT-TYPE
SYNTAX INTEGER (0..65535)
ACCESS read-only
STATUS optional
DESCRIPTION
        " "
::= { outlet24PDU1 2 }

current24PDU1 OBJECT-TYPE
SYNTAX INTEGER (0..65535)
ACCESS read-only
STATUS optional
DESCRIPTION
        " "
::= { outlet24PDU1 3 }

power24PDU1 OBJECT-TYPE
SYNTAX INTEGER (0..65535)
ACCESS read-only
STATUS optional
DESCRIPTION
        " "
::= { outlet24PDU1 4 }

pf24PDU1 OBJECT-TYPE
SYNTAX INTEGER (0..65535)
ACCESS read-only
STATUS optional
DESCRIPTION
        " "
::= { outlet24PDU1 5 }

energy24PDU1 OBJECT-TYPE
SYNTAX INTEGER (0..65535)
ACCESS read-only
STATUS optional
DESCRIPTION
        " "
::= { outlet24PDU1 6 }

switch25PDU1 OBJECT-TYPE
SYNTAX INTEGER (0..3)
ACCESS read-write
STATUS optional
DESCRIPTION
        " "
::= { outlet25PDU1 1 }

voltage25PDU1 OBJECT-TYPE
SYNTAX INTEGER (0..65535)
ACCESS read-only
STATUS optional
DESCRIPTION
        " "
::= { outlet25PDU1 2 }

current25PDU1 OBJECT-TYPE
SYNTAX INTEGER (0..65535)
ACCESS read-only
STATUS optional
DESCRIPTION
        " "
::= { outlet25PDU1 3 }

power25PDU1 OBJECT-TYPE
SYNTAX INTEGER (0..65535)
ACCESS read-only
STATUS optional
DESCRIPTION
        " "
::= { outlet25PDU1 4 }

pf25PDU1 OBJECT-TYPE
SYNTAX INTEGER (0..65535)
ACCESS read-only
STATUS optional
DESCRIPTION
        " "
::= { outlet25PDU1 5 }

energy25PDU1 OBJECT-TYPE
SYNTAX INTEGER (0..65535)
ACCESS read-only
STATUS optional
DESCRIPTION
        " "
::= { outlet25PDU1 6 }

switch26PDU1 OBJECT-TYPE
SYNTAX INTEGER (0..3)
ACCESS read-write
STATUS optional
DESCRIPTION
        " "
::= { outlet26PDU1 1 }

voltage26PDU1 OBJECT-TYPE
SYNTAX INTEGER (0..65535)
ACCESS read-only
STATUS optional
DESCRIPTION
        " "
::= { outlet26PDU1 2 }

current26PDU1 OBJECT-TYPE
SYNTAX INTEGER (0..65535)
ACCESS read-only
STATUS optional
DESCRIPTION
        " "
::= { outlet26PDU1 3 }

power26PDU1 OBJECT-TYPE
SYNTAX INTEGER (0..65535)
ACCESS read-only
STATUS optional
DESCRIPTION
        " "
::= { outlet26PDU1 4 }

pf26PDU1 OBJECT-TYPE
SYNTAX INTEGER (0..65535)
ACCESS read-only
STATUS optional
DESCRIPTION
        " "
::= { outlet26PDU1 5 }

energy26PDU1 OBJECT-TYPE
SYNTAX INTEGER (0..65535)
ACCESS read-only
STATUS optional
DESCRIPTION
        " "
::= { outlet26PDU1 6 }

switch27PDU1 OBJECT-TYPE
SYNTAX INTEGER (0..3)
ACCESS read-write
STATUS optional
DESCRIPTION
        " "
::= { outlet27PDU1 1 }

voltage27PDU1 OBJECT-TYPE
SYNTAX INTEGER (0..65535)
ACCESS read-only
STATUS optional
DESCRIPTION
        " "
::= { outlet27PDU1 2 }

current27PDU1 OBJECT-TYPE
SYNTAX INTEGER (0..65535)
ACCESS read-only
STATUS optional
DESCRIPTION
        " "
::= { outlet27PDU1 3 }

power27PDU1 OBJECT-TYPE
SYNTAX INTEGER (0..65535)
ACCESS read-only
STATUS optional
DESCRIPTION
        " "
::= { outlet27PDU1 4 }

pf27PDU1 OBJECT-TYPE
SYNTAX INTEGER (0..65535)
ACCESS read-only
STATUS optional
DESCRIPTION
        " "
::= { outlet27PDU1 5 }

energy27PDU1 OBJECT-TYPE
SYNTAX INTEGER (0..65535)
ACCESS read-only
STATUS optional
DESCRIPTION
        " "
::= { outlet27PDU1 6 }

switch28PDU1 OBJECT-TYPE
SYNTAX INTEGER (0..3)
ACCESS read-write
STATUS optional
DESCRIPTION
        " "
::= { outlet28PDU1 1 }

voltage28PDU1 OBJECT-TYPE
SYNTAX INTEGER (0..65535)
ACCESS read-only
STATUS optional
DESCRIPTION
        " "
::= { outlet28PDU1 2 }

current28PDU1 OBJECT-TYPE
SYNTAX INTEGER (0..65535)
ACCESS read-only
STATUS optional
DESCRIPTION
        " "
::= { outlet28PDU1 3 }

power28PDU1 OBJECT-TYPE
SYNTAX INTEGER (0..65535)
ACCESS read-only
STATUS optional
DESCRIPTION
        " "
::= { outlet28PDU1 4 }

pf28PDU1 OBJECT-TYPE
SYNTAX INTEGER (0..65535)
ACCESS read-only
STATUS optional
DESCRIPTION
        " "
::= { outlet28PDU1 5 }

energy28PDU1 OBJECT-TYPE
SYNTAX INTEGER (0..65535)
ACCESS read-only
STATUS optional
DESCRIPTION
        " "
::= { outlet28PDU1 6 }

switch29PDU1 OBJECT-TYPE
SYNTAX INTEGER (0..3)
ACCESS read-write
STATUS optional
DESCRIPTION
        " "
::= { outlet29PDU1 1 }

voltage29PDU1 OBJECT-TYPE
SYNTAX INTEGER (0..65535)
ACCESS read-only
STATUS optional
DESCRIPTION
        " "
::= { outlet29PDU1 2 }

current29PDU1 OBJECT-TYPE
SYNTAX INTEGER (0..65535)
ACCESS read-only
STATUS optional
DESCRIPTION
        " "
::= { outlet29PDU1 3 }

power29PDU1 OBJECT-TYPE
SYNTAX INTEGER (0..65535)
ACCESS read-only
STATUS optional
DESCRIPTION
        " "
::= { outlet29PDU1 4 }

pf29PDU1 OBJECT-TYPE
SYNTAX INTEGER (0..65535)
ACCESS read-only
STATUS optional
DESCRIPTION
        " "
::= { outlet29PDU1 5 }

energy29PDU1 OBJECT-TYPE
SYNTAX INTEGER (0..65535)
ACCESS read-only
STATUS optional
DESCRIPTION
        " "
::= { outlet29PDU1 6 }

switch30PDU1 OBJECT-TYPE
SYNTAX INTEGER (0..3)
ACCESS read-write
STATUS optional
DESCRIPTION
        " "
::= { outlet30PDU1 1 }

voltage30PDU1 OBJECT-TYPE
SYNTAX INTEGER (0..65535)
ACCESS read-only
STATUS optional
DESCRIPTION
        " "
::= { outlet30PDU1 2 }

current30PDU1 OBJECT-TYPE
SYNTAX INTEGER (0..65535)
ACCESS read-only
STATUS optional
DESCRIPTION
        " "
::= { outlet30PDU1 3 }

power30PDU1 OBJECT-TYPE
SYNTAX INTEGER (0..65535)
ACCESS read-only
STATUS optional
DESCRIPTION
        " "
::= { outlet30PDU1 4 }

pf30PDU1 OBJECT-TYPE
SYNTAX INTEGER (0..65535)
ACCESS read-only
STATUS optional
DESCRIPTION
        " "
::= { outlet30PDU1 5 }

energy30PDU1 OBJECT-TYPE
SYNTAX INTEGER (0..65535)
ACCESS read-only
STATUS optional
DESCRIPTION
        " "
::= { outlet30PDU1 6 }

switch31PDU1 OBJECT-TYPE
SYNTAX INTEGER (0..3)
ACCESS read-write
STATUS optional
DESCRIPTION
        " "
::= { outlet31PDU1 1 }

voltage31PDU1 OBJECT-TYPE
SYNTAX INTEGER (0..65535)
ACCESS read-only
STATUS optional
DESCRIPTION
        " "
::= { outlet31PDU1 2 }

current31PDU1 OBJECT-TYPE
SYNTAX INTEGER (0..65535)
ACCESS read-only
STATUS optional
DESCRIPTION
        " "
::= { outlet31PDU1 3 }

power31PDU1 OBJECT-TYPE
SYNTAX INTEGER (0..65535)
ACCESS read-only
STATUS optional
DESCRIPTION
        " "
::= { outlet31PDU1 4 }

pf31PDU1 OBJECT-TYPE
SYNTAX INTEGER (0..65535)
ACCESS read-only
STATUS optional
DESCRIPTION
        " "
::= { outlet31PDU1 5 }

energy31PDU1 OBJECT-TYPE
SYNTAX INTEGER (0..65535)
ACCESS read-only
STATUS optional
DESCRIPTION
        " "
::= { outlet31PDU1 6 }

switch32PDU1 OBJECT-TYPE
SYNTAX INTEGER (0..3)
ACCESS read-write
STATUS optional
DESCRIPTION
        " "
::= { outlet32PDU1 1 }

voltage32PDU1 OBJECT-TYPE
SYNTAX INTEGER (0..65535)
ACCESS read-only
STATUS optional
DESCRIPTION
        " "
::= { outlet32PDU1 2 }

current32PDU1 OBJECT-TYPE
SYNTAX INTEGER (0..65535)
ACCESS read-only
STATUS optional
DESCRIPTION
        " "
::= { outlet32PDU1 3 }

power32PDU1 OBJECT-TYPE
SYNTAX INTEGER (0..65535)
ACCESS read-only
STATUS optional
DESCRIPTION
        " "
::= { outlet32PDU1 4 }

pf32PDU1 OBJECT-TYPE
SYNTAX INTEGER (0..65535)
ACCESS read-only
STATUS optional
DESCRIPTION
        " "
::= { outlet32PDU1 5 }

energy32PDU1 OBJECT-TYPE
SYNTAX INTEGER (0..65535)
ACCESS read-only
STATUS optional
DESCRIPTION
        " "
::= { outlet32PDU1 6 }

switch33PDU1 OBJECT-TYPE
SYNTAX INTEGER (0..3)
ACCESS read-write
STATUS optional
DESCRIPTION
        " "
::= { outlet33PDU1 1 }

voltage33PDU1 OBJECT-TYPE
SYNTAX INTEGER (0..65535)
ACCESS read-only
STATUS optional
DESCRIPTION
        " "
::= { outlet33PDU1 2 }

current33PDU1 OBJECT-TYPE
SYNTAX INTEGER (0..65535)
ACCESS read-only
STATUS optional
DESCRIPTION
        " "
::= { outlet33PDU1 3 }

power33PDU1 OBJECT-TYPE
SYNTAX INTEGER (0..65535)
ACCESS read-only
STATUS optional
DESCRIPTION
        " "
::= { outlet33PDU1 4 }

pf33PDU1 OBJECT-TYPE
SYNTAX INTEGER (0..65535)
ACCESS read-only
STATUS optional
DESCRIPTION
        " "
::= { outlet33PDU1 5 }

energy33PDU1 OBJECT-TYPE
SYNTAX INTEGER (0..65535)
ACCESS read-only
STATUS optional
DESCRIPTION
        " "
::= { outlet33PDU1 6 }

switch34PDU1 OBJECT-TYPE
SYNTAX INTEGER (0..3)
ACCESS read-write
STATUS optional
DESCRIPTION
        " "
::= { outlet34PDU1 1 }

voltage34PDU1 OBJECT-TYPE
SYNTAX INTEGER (0..65535)
ACCESS read-only
STATUS optional
DESCRIPTION
        " "
::= { outlet34PDU1 2 }

current34PDU1 OBJECT-TYPE
SYNTAX INTEGER (0..65535)
ACCESS read-only
STATUS optional
DESCRIPTION
        " "
::= { outlet34PDU1 3 }

power34PDU1 OBJECT-TYPE
SYNTAX INTEGER (0..65535)
ACCESS read-only
STATUS optional
DESCRIPTION
        " "
::= { outlet34PDU1 4 }

pf34PDU1 OBJECT-TYPE
SYNTAX INTEGER (0..65535)
ACCESS read-only
STATUS optional
DESCRIPTION
        " "
::= { outlet34PDU1 5 }

energy34PDU1 OBJECT-TYPE
SYNTAX INTEGER (0..65535)
ACCESS read-only
STATUS optional
DESCRIPTION
        " "
::= { outlet34PDU1 6 }

switch35PDU1 OBJECT-TYPE
SYNTAX INTEGER (0..3)
ACCESS read-write
STATUS optional
DESCRIPTION
        " "
::= { outlet35PDU1 1 }

voltage35PDU1 OBJECT-TYPE
SYNTAX INTEGER (0..65535)
ACCESS read-only
STATUS optional
DESCRIPTION
        " "
::= { outlet35PDU1 2 }

current35PDU1 OBJECT-TYPE
SYNTAX INTEGER (0..65535)
ACCESS read-only
STATUS optional
DESCRIPTION
        " "
::= { outlet35PDU1 3 }

power35PDU1 OBJECT-TYPE
SYNTAX INTEGER (0..65535)
ACCESS read-only
STATUS optional
DESCRIPTION
        " "
::= { outlet35PDU1 4 }

pf35PDU1 OBJECT-TYPE
SYNTAX INTEGER (0..65535)
ACCESS read-only
STATUS optional
DESCRIPTION
        " "
::= { outlet35PDU1 5 }

energy35PDU1 OBJECT-TYPE
SYNTAX INTEGER (0..65535)
ACCESS read-only
STATUS optional
DESCRIPTION
        " "
::= { outlet35PDU1 6 }

switch36PDU1 OBJECT-TYPE
SYNTAX INTEGER (0..3)
ACCESS read-write
STATUS optional
DESCRIPTION
        " "
::= { outlet36PDU1 1 }

voltage36PDU1 OBJECT-TYPE
SYNTAX INTEGER (0..65535)
ACCESS read-only
STATUS optional
DESCRIPTION
        " "
::= { outlet36PDU1 2 }

current36PDU1 OBJECT-TYPE
SYNTAX INTEGER (0..65535)
ACCESS read-only
STATUS optional
DESCRIPTION
        " "
::= { outlet36PDU1 3 }

power36PDU1 OBJECT-TYPE
SYNTAX INTEGER (0..65535)
ACCESS read-only
STATUS optional
DESCRIPTION
        " "
::= { outlet36PDU1 4 }

pf36PDU1 OBJECT-TYPE
SYNTAX INTEGER (0..65535)
ACCESS read-only
STATUS optional
DESCRIPTION
        " "
::= { outlet36PDU1 5 }

energy36PDU1 OBJECT-TYPE
SYNTAX INTEGER (0..65535)
ACCESS read-only
STATUS optional
DESCRIPTION
        " "
::= { outlet36PDU1 6 }

sensor1 OBJECT IDENTIFIER ::= { pdu1 4 }

temperature1PDU1 OBJECT-TYPE
SYNTAX INTEGER (0..65535)
ACCESS read-only
STATUS optional
DESCRIPTION
        " "
::= { sensor1 1 }

humidity1PDU1 OBJECT-TYPE
SYNTAX INTEGER (0..65535)
ACCESS read-only
STATUS optional
DESCRIPTION
        " "
::= { sensor1 2 }

temperature2PDU1 OBJECT-TYPE
SYNTAX INTEGER (0..65535)
ACCESS read-only
STATUS optional
DESCRIPTION
        " "
::= { sensor1 3 }

humidity2PDU1 OBJECT-TYPE
SYNTAX INTEGER (0..65535)
ACCESS read-only
STATUS optional
DESCRIPTION
        " "
::= { sensor1 4 }

inputStatus1PDU1 OBJECT-TYPE
SYNTAX INTEGER (0..1)
ACCESS read-only
STATUS optional
DESCRIPTION
        " "
::= { sensor1 5 }

inputStatus2PDU1 OBJECT-TYPE
SYNTAX INTEGER (0..1)
ACCESS read-only
STATUS optional
DESCRIPTION
        " "
::= { sensor1 6 }

inputStatus3PDU1 OBJECT-TYPE
SYNTAX INTEGER (0..1)
ACCESS read-only
STATUS optional
DESCRIPTION
        " "
::= { sensor1 7 }

inputStatus4PDU1 OBJECT-TYPE
SYNTAX INTEGER (0..1)
ACCESS read-only
STATUS optional
DESCRIPTION
        " "
::= { sensor1 8 }

doStatus1PDU1 OBJECT-TYPE
SYNTAX INTEGER (0..1)
ACCESS read-only
STATUS optional
DESCRIPTION
        " "
::= { sensor1 9 }

doStatus2PDU1 OBJECT-TYPE
SYNTAX INTEGER (0..1)
ACCESS read-only
STATUS optional
DESCRIPTION
        " "
::= { sensor1 10 }

baseinfo1 OBJECT IDENTIFIER ::= { pdu2 1 }

cascadeAlarmPDU2 OBJECT-TYPE
SYNTAX INTEGER (0..3)
ACCESS read-only
STATUS optional
DESCRIPTION
        " "
::= { baseinfo1 1 }

deviceNamePDU2 OBJECT-TYPE
SYNTAX DisplayString (SIZE (32))
ACCESS read-write
STATUS optional
DESCRIPTION
        " "
::= { baseinfo1 2 }

outletNumberPDU2 OBJECT-TYPE
SYNTAX INTEGER (0..36)
ACCESS read-only
STATUS optional
DESCRIPTION
        " "
::= { baseinfo1 3 }

temphum1WarnStatPDU2 OBJECT-TYPE
SYNTAX INTEGER (0..127)
ACCESS read-only
STATUS optional
DESCRIPTION
        " "
::= { baseinfo1 4 }

temphum2WarnStatPDU2 OBJECT-TYPE
SYNTAX INTEGER (0..127)
ACCESS read-only
STATUS optional
DESCRIPTION
        " "
::= { baseinfo1 5 }

input1WarnStatPDU2 OBJECT-TYPE
SYNTAX INTEGER (0..1)
ACCESS read-only
STATUS optional
DESCRIPTION
        " "
::= { baseinfo1 6 }

input2WarnStatPDU2 OBJECT-TYPE
SYNTAX INTEGER (0..1)
ACCESS read-only
STATUS optional
DESCRIPTION
        " "
::= { baseinfo1 7 }

input3WarnStatPDU2 OBJECT-TYPE
SYNTAX INTEGER (0..1)
ACCESS read-only
STATUS optional
DESCRIPTION
        " "
::= { baseinfo1 8 }

input4WarnStatPDU2 OBJECT-TYPE
SYNTAX INTEGER (0..1)
ACCESS read-only
STATUS optional
DESCRIPTION
        " "
::= { baseinfo1 9 }

currentL1WarnStatPDU2 OBJECT-TYPE
SYNTAX INTEGER (0..127)
ACCESS read-only
STATUS optional
DESCRIPTION
        " "
::= { baseinfo1 10 }

currentL2WarnStatPDU2 OBJECT-TYPE
SYNTAX INTEGER (0..127)
ACCESS read-only
STATUS optional
DESCRIPTION
        " "
::= { baseinfo1 11 }

currentL3WarnStatPDU2 OBJECT-TYPE
SYNTAX INTEGER (0..127)
ACCESS read-only
STATUS optional
DESCRIPTION
        " "
::= { baseinfo1 12 }

voltageL1WarnStatPDU2 OBJECT-TYPE
SYNTAX INTEGER (0..127)
ACCESS read-only
STATUS optional
DESCRIPTION
        " "
::= { baseinfo1 13 }

voltageL2WarnStatPDU2 OBJECT-TYPE
SYNTAX INTEGER (0..127)
ACCESS read-only
STATUS optional
DESCRIPTION
        " "
::= { baseinfo1 14 }

voltageL3WarnStatPDU2 OBJECT-TYPE
SYNTAX INTEGER (0..127)
ACCESS read-only
STATUS optional
DESCRIPTION
        " "
::= { baseinfo1 15 }

outlet1WarnStatPDU2 OBJECT-TYPE
SYNTAX INTEGER (0..127)
ACCESS read-only
STATUS optional
DESCRIPTION
        " "
::= { baseinfo1 16 }

outlet2WarnStatPDU2 OBJECT-TYPE
SYNTAX INTEGER (0..127)
ACCESS read-only
STATUS optional
DESCRIPTION
        " "
::= { baseinfo1 17 }

outlet3WarnStatPDU2 OBJECT-TYPE
SYNTAX INTEGER (0..127)
ACCESS read-only
STATUS optional
DESCRIPTION
        " "
::= { baseinfo1 18 }

outlet4WarnStatPDU2 OBJECT-TYPE
SYNTAX INTEGER (0..127)
ACCESS read-only
STATUS optional
DESCRIPTION
        " "
::= { baseinfo1 19 }

outlet5WarnStatPDU2 OBJECT-TYPE
SYNTAX INTEGER (0..127)
ACCESS read-only
STATUS optional
DESCRIPTION
        " "
::= { baseinfo1 20 }

outlet6WarnStatPDU2 OBJECT-TYPE
SYNTAX INTEGER (0..127)
ACCESS read-only
STATUS optional
DESCRIPTION
        " "
::= { baseinfo1 21 }

outlet7WarnStatPDU2 OBJECT-TYPE
SYNTAX INTEGER (0..127)
ACCESS read-only
STATUS optional
DESCRIPTION
        " "
::= { baseinfo1 22 }

outlet8WarnStatPDU2 OBJECT-TYPE
SYNTAX INTEGER (0..127)
ACCESS read-only
STATUS optional
DESCRIPTION
        " "
::= { baseinfo1 23 }

outlet9WarnStatPDU2 OBJECT-TYPE
SYNTAX INTEGER (0..127)
ACCESS read-only
STATUS optional
DESCRIPTION
        " "
::= { baseinfo1 24 }

outlet10WarnStatPDU2 OBJECT-TYPE
SYNTAX INTEGER (0..127)
ACCESS read-only
STATUS optional
DESCRIPTION
        " "
::= { baseinfo1 25 }

outlet11WarnStatPDU2 OBJECT-TYPE
SYNTAX INTEGER (0..127)
ACCESS read-only
STATUS optional
DESCRIPTION
        " "
::= { baseinfo1 26 }

outlet12WarnStatPDU2 OBJECT-TYPE
SYNTAX INTEGER (0..127)
ACCESS read-only
STATUS optional
DESCRIPTION
        " "
::= { baseinfo1 27 }

outlet13WarnStatPDU2 OBJECT-TYPE
SYNTAX INTEGER (0..127)
ACCESS read-only
STATUS optional
DESCRIPTION
        " "
::= { baseinfo1 28 }

outlet14WarnStatPDU2 OBJECT-TYPE
SYNTAX INTEGER (0..127)
ACCESS read-only
STATUS optional
DESCRIPTION
        " "
::= { baseinfo1 29 }

outlet15WarnStatPDU2 OBJECT-TYPE
SYNTAX INTEGER (0..127)
ACCESS read-only
STATUS optional
DESCRIPTION
        " "
::= { baseinfo1 30 }

outlet16WarnStatPDU2 OBJECT-TYPE
SYNTAX INTEGER (0..127)
ACCESS read-only
STATUS optional
DESCRIPTION
        " "
::= { baseinfo1 31 }

outlet17WarnStatPDU2 OBJECT-TYPE
SYNTAX INTEGER (0..127)
ACCESS read-only
STATUS optional
DESCRIPTION
        " "
::= { baseinfo1 32 }

outlet18WarnStatPDU2 OBJECT-TYPE
SYNTAX INTEGER (0..127)
ACCESS read-only
STATUS optional
DESCRIPTION
        " "
::= { baseinfo1 33 }

outlet19WarnStatPDU2 OBJECT-TYPE
SYNTAX INTEGER (0..127)
ACCESS read-only
STATUS optional
DESCRIPTION
        " "
::= { baseinfo1 34 }

outlet20WarnStatPDU2 OBJECT-TYPE
SYNTAX INTEGER (0..127)
ACCESS read-only
STATUS optional
DESCRIPTION
        " "
::= { baseinfo1 35 }

outlet21WarnStatPDU2 OBJECT-TYPE
SYNTAX INTEGER (0..127)
ACCESS read-only
STATUS optional
DESCRIPTION
        " "
::= { baseinfo1 36 }

outlet22WarnStatPDU2 OBJECT-TYPE
SYNTAX INTEGER (0..127)
ACCESS read-only
STATUS optional
DESCRIPTION
        " "
::= { baseinfo1 37 }

outlet23WarnStatPDU2 OBJECT-TYPE
SYNTAX INTEGER (0..127)
ACCESS read-only
STATUS optional
DESCRIPTION
        " "
::= { baseinfo1 38 }

outlet24WarnStatPDU2 OBJECT-TYPE
SYNTAX INTEGER (0..127)
ACCESS read-only
STATUS optional
DESCRIPTION
        " "
::= { baseinfo1 39 }

outlet25WarnStatPDU2 OBJECT-TYPE
SYNTAX INTEGER (0..127)
ACCESS read-only
STATUS optional
DESCRIPTION
        " "
::= { baseinfo1 40 }

outlet26WarnStatPDU2 OBJECT-TYPE
SYNTAX INTEGER (0..127)
ACCESS read-only
STATUS optional
DESCRIPTION
        " "
::= { baseinfo1 41 }

outlet27WarnStatPDU2 OBJECT-TYPE
SYNTAX INTEGER (0..127)
ACCESS read-only
STATUS optional
DESCRIPTION
        " "
::= { baseinfo1 42 }

outlet28WarnStatPDU2 OBJECT-TYPE
SYNTAX INTEGER (0..127)
ACCESS read-only
STATUS optional
DESCRIPTION
        " "
::= { baseinfo1 43 }

outlet29WarnStatPDU2 OBJECT-TYPE
SYNTAX INTEGER (0..127)
ACCESS read-only
STATUS optional
DESCRIPTION
        " "
::= { baseinfo1 44 }

outlet30WarnStatPDU2 OBJECT-TYPE
SYNTAX INTEGER (0..127)
ACCESS read-only
STATUS optional
DESCRIPTION
        " "
::= { baseinfo1 45 }

outlet31WarnStatPDU2 OBJECT-TYPE
SYNTAX INTEGER (0..127)
ACCESS read-only
STATUS optional
DESCRIPTION
        " "
::= { baseinfo1 46 }

outlet32WarnStatPDU2 OBJECT-TYPE
SYNTAX INTEGER (0..127)
ACCESS read-only
STATUS optional
DESCRIPTION
        " "
::= { baseinfo1 47 }

outlet33WarnStatPDU2 OBJECT-TYPE
SYNTAX INTEGER (0..127)
ACCESS read-only
STATUS optional
DESCRIPTION
        " "
::= { baseinfo1 48 }

outlet34WarnStatPDU2 OBJECT-TYPE
SYNTAX INTEGER (0..127)
ACCESS read-only
STATUS optional
DESCRIPTION
        " "
::= { baseinfo1 49 }

outlet35WarnStatPDU2 OBJECT-TYPE
SYNTAX INTEGER (0..127)
ACCESS read-only
STATUS optional
DESCRIPTION
        " "
::= { baseinfo1 50 }

outlet36WarnStatPDU2 OBJECT-TYPE
SYNTAX INTEGER (0..127)
ACCESS read-only
STATUS optional
DESCRIPTION
        " "
::= { baseinfo1 51 }

input1 OBJECT IDENTIFIER ::= { pdu2 2 }

currentL1PDU2 OBJECT-TYPE
SYNTAX INTEGER (0..65535)
ACCESS read-only
STATUS optional
DESCRIPTION
        " "
::= { input1 1 }

voltageL1PDU2 OBJECT-TYPE
SYNTAX INTEGER (0..65535)
ACCESS read-only
STATUS optional
DESCRIPTION
        " "
::= { input1 2 }

powerL1PDU2 OBJECT-TYPE
SYNTAX INTEGER (0..65535)
ACCESS read-only
STATUS optional
DESCRIPTION
        " "
::= { input1 3 }

pfL1PDU2 OBJECT-TYPE
SYNTAX INTEGER (0..65535)
ACCESS read-only
STATUS optional
DESCRIPTION
        " "
::= { input1 4 }

energyL1PDU2 OBJECT-TYPE
SYNTAX INTEGER (0..65535)
ACCESS read-only
STATUS optional
DESCRIPTION
        " "
::= { input1 5 }

currentL2PDU2 OBJECT-TYPE
SYNTAX INTEGER (0..65535)
ACCESS read-only
STATUS optional
DESCRIPTION
        " "
::= { input1 6 }

voltageL2PDU2 OBJECT-TYPE
SYNTAX INTEGER (0..65535)
ACCESS read-only
STATUS optional
DESCRIPTION
        " "
::= { input1 7 }

powerL2PDU2 OBJECT-TYPE
SYNTAX INTEGER (0..65535)
ACCESS read-only
STATUS optional
DESCRIPTION
        " "
::= { input1 8 }

pfL2PDU2 OBJECT-TYPE
SYNTAX INTEGER (0..65535)
ACCESS read-only
STATUS optional
DESCRIPTION
        " "
::= { input1 9 }

energyL2PDU2 OBJECT-TYPE
SYNTAX INTEGER (0..65535)
ACCESS read-only
STATUS optional
DESCRIPTION
        " "
::= { input1 10 }

currentL3PDU2 OBJECT-TYPE
SYNTAX INTEGER (0..65535)
ACCESS read-only
STATUS optional
DESCRIPTION
        " "
::= { input1 11 }

voltageL3PDU2 OBJECT-TYPE
SYNTAX INTEGER (0..65535)
ACCESS read-only
STATUS optional
DESCRIPTION
        " "
::= { input1 12 }

powerL3PDU2 OBJECT-TYPE
SYNTAX INTEGER (0..65535)
ACCESS read-only
STATUS optional
DESCRIPTION
        " "
::= { input1 13 }

pfL3PDU2 OBJECT-TYPE
SYNTAX INTEGER (0..65535)
ACCESS read-only
STATUS optional
DESCRIPTION
        " "
::= { input1 14 }

energyL3PDU2 OBJECT-TYPE
SYNTAX INTEGER (0..65535)
ACCESS read-only
STATUS optional
DESCRIPTION
        " "
::= { input1 15 }

outletinfo1 OBJECT IDENTIFIER ::= { pdu2 3 }

outlet1PDU2 OBJECT IDENTIFIER ::= { outletinfo1 1 }

outlet2PDU2 OBJECT IDENTIFIER ::= { outletinfo1 2 }

outlet3PDU2 OBJECT IDENTIFIER ::= { outletinfo1 3 }

outlet4PDU2 OBJECT IDENTIFIER ::= { outletinfo1 4 }

outlet5PDU2 OBJECT IDENTIFIER ::= { outletinfo1 5 }

outlet6PDU2 OBJECT IDENTIFIER ::= { outletinfo1 6 }

outlet7PDU2 OBJECT IDENTIFIER ::= { outletinfo1 7 }

outlet8PDU2 OBJECT IDENTIFIER ::= { outletinfo1 8 }

outlet9PDU2 OBJECT IDENTIFIER ::= { outletinfo1 9 }

outlet10PDU2 OBJECT IDENTIFIER ::= { outletinfo1 10 }

outlet11PDU2 OBJECT IDENTIFIER ::= { outletinfo1 11 }

outlet12PDU2 OBJECT IDENTIFIER ::= { outletinfo1 12 }

outlet13PDU2 OBJECT IDENTIFIER ::= { outletinfo1 13 }

outlet14PDU2 OBJECT IDENTIFIER ::= { outletinfo1 14 }

outlet15PDU2 OBJECT IDENTIFIER ::= { outletinfo1 15 }

outlet16PDU2 OBJECT IDENTIFIER ::= { outletinfo1 16 }

outlet17PDU2 OBJECT IDENTIFIER ::= { outletinfo1 17 }

outlet18PDU2 OBJECT IDENTIFIER ::= { outletinfo1 18 }

outlet19PDU2 OBJECT IDENTIFIER ::= { outletinfo1 19 }

outlet20PDU2 OBJECT IDENTIFIER ::= { outletinfo1 20 }

outlet21PDU2 OBJECT IDENTIFIER ::= { outletinfo1 21 }

outlet22PDU2 OBJECT IDENTIFIER ::= { outletinfo1 22 }

outlet23PDU2 OBJECT IDENTIFIER ::= { outletinfo1 23 }

outlet24PDU2 OBJECT IDENTIFIER ::= { outletinfo1 24 }

outlet25PDU2 OBJECT IDENTIFIER ::= { outletinfo1 25 }

outlet26PDU2 OBJECT IDENTIFIER ::= { outletinfo1 26 }

outlet27PDU2 OBJECT IDENTIFIER ::= { outletinfo1 27 }

outlet28PDU2 OBJECT IDENTIFIER ::= { outletinfo1 28 }

outlet29PDU2 OBJECT IDENTIFIER ::= { outletinfo1 29 }

outlet30PDU2 OBJECT IDENTIFIER ::= { outletinfo1 30 }

outlet31PDU2 OBJECT IDENTIFIER ::= { outletinfo1 31 }

outlet32PDU2 OBJECT IDENTIFIER ::= { outletinfo1 32 }

outlet33PDU2 OBJECT IDENTIFIER ::= { outletinfo1 33 }

outlet34PDU2 OBJECT IDENTIFIER ::= { outletinfo1 34 }

outlet35PDU2 OBJECT IDENTIFIER ::= { outletinfo1 35 }

outlet36PDU2 OBJECT IDENTIFIER ::= { outletinfo1 36 }

switch1PDU2 OBJECT-TYPE
SYNTAX INTEGER (0..3)
ACCESS read-write
STATUS optional
DESCRIPTION
        " "
::= { outlet1PDU2 1 }

voltage1PDU2 OBJECT-TYPE
SYNTAX INTEGER (0..65535)
ACCESS read-only
STATUS optional
DESCRIPTION
        " "
::= { outlet1PDU2 2 }

current1PDU2 OBJECT-TYPE
SYNTAX INTEGER (0..65535)
ACCESS read-only
STATUS optional
DESCRIPTION
        " "
::= { outlet1PDU2 3 }

power1PDU2 OBJECT-TYPE
SYNTAX INTEGER (0..65535)
ACCESS read-only
STATUS optional
DESCRIPTION
        " "
::= { outlet1PDU2 4 }

pf1PDU2 OBJECT-TYPE
SYNTAX INTEGER (0..65535)
ACCESS read-only
STATUS optional
DESCRIPTION
        " "
::= { outlet1PDU2 5 }

energy1PDU2 OBJECT-TYPE
SYNTAX INTEGER (0..65535)
ACCESS read-only
STATUS optional
DESCRIPTION
        " "
::= { outlet1PDU2 6 }

switch2PDU2 OBJECT-TYPE
SYNTAX INTEGER (0..3)
ACCESS read-write
STATUS optional
DESCRIPTION
        " "
::= { outlet2PDU2 1 }

voltage2PDU2 OBJECT-TYPE
SYNTAX INTEGER (0..65535)
ACCESS read-only
STATUS optional
DESCRIPTION
        " "
::= { outlet2PDU2 2 }

current2PDU2 OBJECT-TYPE
SYNTAX INTEGER (0..65535)
ACCESS read-only
STATUS optional
DESCRIPTION
        " "
::= { outlet2PDU2 3 }

power2PDU2 OBJECT-TYPE
SYNTAX INTEGER (0..65535)
ACCESS read-only
STATUS optional
DESCRIPTION
        " "
::= { outlet2PDU2 4 }

pf2PDU2 OBJECT-TYPE
SYNTAX INTEGER (0..65535)
ACCESS read-only
STATUS optional
DESCRIPTION
        " "
::= { outlet2PDU2 5 }

energy2PDU2 OBJECT-TYPE
SYNTAX INTEGER (0..65535)
ACCESS read-only
STATUS optional
DESCRIPTION
        " "
::= { outlet2PDU2 6 }

switch3PDU2 OBJECT-TYPE
SYNTAX INTEGER (0..3)
ACCESS read-write
STATUS optional
DESCRIPTION
        " "
::= { outlet3PDU2 1 }

voltage3PDU2 OBJECT-TYPE
SYNTAX INTEGER (0..65535)
ACCESS read-only
STATUS optional
DESCRIPTION
        " "
::= { outlet3PDU2 2 }

current3PDU2 OBJECT-TYPE
SYNTAX INTEGER (0..65535)
ACCESS read-only
STATUS optional
DESCRIPTION
        " "
::= { outlet3PDU2 3 }

power3PDU2 OBJECT-TYPE
SYNTAX INTEGER (0..65535)
ACCESS read-only
STATUS optional
DESCRIPTION
        " "
::= { outlet3PDU2 4 }

pf3PDU2 OBJECT-TYPE
SYNTAX INTEGER (0..65535)
ACCESS read-only
STATUS optional
DESCRIPTION
        " "
::= { outlet3PDU2 5 }

energy3PDU2 OBJECT-TYPE
SYNTAX INTEGER (0..65535)
ACCESS read-only
STATUS optional
DESCRIPTION
        " "
::= { outlet3PDU2 6 }

switch4PDU2 OBJECT-TYPE
SYNTAX INTEGER (0..3)
ACCESS read-write
STATUS optional
DESCRIPTION
        " "
::= { outlet4PDU2 1 }

voltage4PDU2 OBJECT-TYPE
SYNTAX INTEGER (0..65535)
ACCESS read-only
STATUS optional
DESCRIPTION
        " "
::= { outlet4PDU2 2 }

current4PDU2 OBJECT-TYPE
SYNTAX INTEGER (0..65535)
ACCESS read-only
STATUS optional
DESCRIPTION
        " "
::= { outlet4PDU2 3 }

power4PDU2 OBJECT-TYPE
SYNTAX INTEGER (0..65535)
ACCESS read-only
STATUS optional
DESCRIPTION
        " "
::= { outlet4PDU2 4 }

pf4PDU2 OBJECT-TYPE
SYNTAX INTEGER (0..65535)
ACCESS read-only
STATUS optional
DESCRIPTION
        " "
::= { outlet4PDU2 5 }

energy4PDU2 OBJECT-TYPE
SYNTAX INTEGER (0..65535)
ACCESS read-only
STATUS optional
DESCRIPTION
        " "
::= { outlet4PDU2 6 }

switch5PDU2 OBJECT-TYPE
SYNTAX INTEGER (0..3)
ACCESS read-write
STATUS optional
DESCRIPTION
        " "
::= { outlet5PDU2 1 }

voltage5PDU2 OBJECT-TYPE
SYNTAX INTEGER (0..65535)
ACCESS read-only
STATUS optional
DESCRIPTION
        " "
::= { outlet5PDU2 2 }

current5PDU2 OBJECT-TYPE
SYNTAX INTEGER (0..65535)
ACCESS read-only
STATUS optional
DESCRIPTION
        " "
::= { outlet5PDU2 3 }

power5PDU2 OBJECT-TYPE
SYNTAX INTEGER (0..65535)
ACCESS read-only
STATUS optional
DESCRIPTION
        " "
::= { outlet5PDU2 4 }

pf5PDU2 OBJECT-TYPE
SYNTAX INTEGER (0..65535)
ACCESS read-only
STATUS optional
DESCRIPTION
        " "
::= { outlet5PDU2 5 }

energy5PDU2 OBJECT-TYPE
SYNTAX INTEGER (0..65535)
ACCESS read-only
STATUS optional
DESCRIPTION
        " "
::= { outlet5PDU2 6 }

switch6PDU2 OBJECT-TYPE
SYNTAX INTEGER (0..3)
ACCESS read-write
STATUS optional
DESCRIPTION
        " "
::= { outlet6PDU2 1 }

voltage6PDU2 OBJECT-TYPE
SYNTAX INTEGER (0..65535)
ACCESS read-only
STATUS optional
DESCRIPTION
        " "
::= { outlet6PDU2 2 }

current6PDU2 OBJECT-TYPE
SYNTAX INTEGER (0..65535)
ACCESS read-only
STATUS optional
DESCRIPTION
        " "
::= { outlet6PDU2 3 }

power6PDU2 OBJECT-TYPE
SYNTAX INTEGER (0..65535)
ACCESS read-only
STATUS optional
DESCRIPTION
        " "
::= { outlet6PDU2 4 }

pf6PDU2 OBJECT-TYPE
SYNTAX INTEGER (0..65535)
ACCESS read-only
STATUS optional
DESCRIPTION
        " "
::= { outlet6PDU2 5 }

energy6PDU2 OBJECT-TYPE
SYNTAX INTEGER (0..65535)
ACCESS read-only
STATUS optional
DESCRIPTION
        " "
::= { outlet6PDU2 6 }

switch7PDU2 OBJECT-TYPE
SYNTAX INTEGER (0..3)
ACCESS read-write
STATUS optional
DESCRIPTION
        " "
::= { outlet7PDU2 1 }

voltage7PDU2 OBJECT-TYPE
SYNTAX INTEGER (0..65535)
ACCESS read-only
STATUS optional
DESCRIPTION
        " "
::= { outlet7PDU2 2 }

current7PDU2 OBJECT-TYPE
SYNTAX INTEGER (0..65535)
ACCESS read-only
STATUS optional
DESCRIPTION
        " "
::= { outlet7PDU2 3 }

power7PDU2 OBJECT-TYPE
SYNTAX INTEGER (0..65535)
ACCESS read-only
STATUS optional
DESCRIPTION
        " "
::= { outlet7PDU2 4 }

pf7PDU2 OBJECT-TYPE
SYNTAX INTEGER (0..65535)
ACCESS read-only
STATUS optional
DESCRIPTION
        " "
::= { outlet7PDU2 5 }

energy7PDU2 OBJECT-TYPE
SYNTAX INTEGER (0..65535)
ACCESS read-only
STATUS optional
DESCRIPTION
        " "
::= { outlet7PDU2 6 }

switch8PDU2 OBJECT-TYPE
SYNTAX INTEGER (0..3)
ACCESS read-write
STATUS optional
DESCRIPTION
        " "
::= { outlet8PDU2 1 }

voltage8PDU2 OBJECT-TYPE
SYNTAX INTEGER (0..65535)
ACCESS read-only
STATUS optional
DESCRIPTION
        " "
::= { outlet8PDU2 2 }

current8PDU2 OBJECT-TYPE
SYNTAX INTEGER (0..65535)
ACCESS read-only
STATUS optional
DESCRIPTION
        " "
::= { outlet8PDU2 3 }

power8PDU2 OBJECT-TYPE
SYNTAX INTEGER (0..65535)
ACCESS read-only
STATUS optional
DESCRIPTION
        " "
::= { outlet8PDU2 4 }

pf8PDU2 OBJECT-TYPE
SYNTAX INTEGER (0..65535)
ACCESS read-only
STATUS optional
DESCRIPTION
        " "
::= { outlet8PDU2 5 }

energy8PDU2 OBJECT-TYPE
SYNTAX INTEGER (0..65535)
ACCESS read-only
STATUS optional
DESCRIPTION
        " "
::= { outlet8PDU2 6 }

switch9PDU2 OBJECT-TYPE
SYNTAX INTEGER (0..3)
ACCESS read-write
STATUS optional
DESCRIPTION
        " "
::= { outlet9PDU2 1 }

voltage9PDU2 OBJECT-TYPE
SYNTAX INTEGER (0..65535)
ACCESS read-only
STATUS optional
DESCRIPTION
        " "
::= { outlet9PDU2 2 }

current9PDU2 OBJECT-TYPE
SYNTAX INTEGER (0..65535)
ACCESS read-only
STATUS optional
DESCRIPTION
        " "
::= { outlet9PDU2 3 }

power9PDU2 OBJECT-TYPE
SYNTAX INTEGER (0..65535)
ACCESS read-only
STATUS optional
DESCRIPTION
        " "
::= { outlet9PDU2 4 }

pf9PDU2 OBJECT-TYPE
SYNTAX INTEGER (0..65535)
ACCESS read-only
STATUS optional
DESCRIPTION
        " "
::= { outlet9PDU2 5 }

energy9PDU2 OBJECT-TYPE
SYNTAX INTEGER (0..65535)
ACCESS read-only
STATUS optional
DESCRIPTION
        " "
::= { outlet9PDU2 6 }

switch10PDU2 OBJECT-TYPE
SYNTAX INTEGER (0..3)
ACCESS read-write
STATUS optional
DESCRIPTION
        " "
::= { outlet10PDU2 1 }

voltage10PDU2 OBJECT-TYPE
SYNTAX INTEGER (0..65535)
ACCESS read-only
STATUS optional
DESCRIPTION
        " "
::= { outlet10PDU2 2 }

current10PDU2 OBJECT-TYPE
SYNTAX INTEGER (0..65535)
ACCESS read-only
STATUS optional
DESCRIPTION
        " "
::= { outlet10PDU2 3 }

power10PDU2 OBJECT-TYPE
SYNTAX INTEGER (0..65535)
ACCESS read-only
STATUS optional
DESCRIPTION
        " "
::= { outlet10PDU2 4 }

pf10PDU2 OBJECT-TYPE
SYNTAX INTEGER (0..65535)
ACCESS read-only
STATUS optional
DESCRIPTION
        " "
::= { outlet10PDU2 5 }

energy10PDU2 OBJECT-TYPE
SYNTAX INTEGER (0..65535)
ACCESS read-only
STATUS optional
DESCRIPTION
        " "
::= { outlet10PDU2 6 }

switch11PDU2 OBJECT-TYPE
SYNTAX INTEGER (0..3)
ACCESS read-write
STATUS optional
DESCRIPTION
        " "
::= { outlet11PDU2 1 }

voltage11PDU2 OBJECT-TYPE
SYNTAX INTEGER (0..65535)
ACCESS read-only
STATUS optional
DESCRIPTION
        " "
::= { outlet11PDU2 2 }

current11PDU2 OBJECT-TYPE
SYNTAX INTEGER (0..65535)
ACCESS read-only
STATUS optional
DESCRIPTION
        " "
::= { outlet11PDU2 3 }

power11PDU2 OBJECT-TYPE
SYNTAX INTEGER (0..65535)
ACCESS read-only
STATUS optional
DESCRIPTION
        " "
::= { outlet11PDU2 4 }

pf11PDU2 OBJECT-TYPE
SYNTAX INTEGER (0..65535)
ACCESS read-only
STATUS optional
DESCRIPTION
        " "
::= { outlet11PDU2 5 }

energy11PDU2 OBJECT-TYPE
SYNTAX INTEGER (0..65535)
ACCESS read-only
STATUS optional
DESCRIPTION
        " "
::= { outlet11PDU2 6 }

switch12PDU2 OBJECT-TYPE
SYNTAX INTEGER (0..3)
ACCESS read-write
STATUS optional
DESCRIPTION
        " "
::= { outlet12PDU2 1 }

voltage12PDU2 OBJECT-TYPE
SYNTAX INTEGER (0..65535)
ACCESS read-only
STATUS optional
DESCRIPTION
        " "
::= { outlet12PDU2 2 }

current12PDU2 OBJECT-TYPE
SYNTAX INTEGER (0..65535)
ACCESS read-only
STATUS optional
DESCRIPTION
        " "
::= { outlet12PDU2 3 }

power12PDU2 OBJECT-TYPE
SYNTAX INTEGER (0..65535)
ACCESS read-only
STATUS optional
DESCRIPTION
        " "
::= { outlet12PDU2 4 }

pf12PDU2 OBJECT-TYPE
SYNTAX INTEGER (0..65535)
ACCESS read-only
STATUS optional
DESCRIPTION
        " "
::= { outlet12PDU2 5 }

energy12PDU2 OBJECT-TYPE
SYNTAX INTEGER (0..65535)
ACCESS read-only
STATUS optional
DESCRIPTION
        " "
::= { outlet12PDU2 6 }

switch13PDU2 OBJECT-TYPE
SYNTAX INTEGER (0..3)
ACCESS read-write
STATUS optional
DESCRIPTION
        " "
::= { outlet13PDU2 1 }

voltage13PDU2 OBJECT-TYPE
SYNTAX INTEGER (0..65535)
ACCESS read-only
STATUS optional
DESCRIPTION
        " "
::= { outlet13PDU2 2 }

current13PDU2 OBJECT-TYPE
SYNTAX INTEGER (0..65535)
ACCESS read-only
STATUS optional
DESCRIPTION
        " "
::= { outlet13PDU2 3 }

power13PDU2 OBJECT-TYPE
SYNTAX INTEGER (0..65535)
ACCESS read-only
STATUS optional
DESCRIPTION
        " "
::= { outlet13PDU2 4 }

pf13PDU2 OBJECT-TYPE
SYNTAX INTEGER (0..65535)
ACCESS read-only
STATUS optional
DESCRIPTION
        " "
::= { outlet13PDU2 5 }

energy13PDU2 OBJECT-TYPE
SYNTAX INTEGER (0..65535)
ACCESS read-only
STATUS optional
DESCRIPTION
        " "
::= { outlet13PDU2 6 }

switch14PDU2 OBJECT-TYPE
SYNTAX INTEGER (0..3)
ACCESS read-write
STATUS optional
DESCRIPTION
        " "
::= { outlet14PDU2 1 }

voltage14PDU2 OBJECT-TYPE
SYNTAX INTEGER (0..65535)
ACCESS read-only
STATUS optional
DESCRIPTION
        " "
::= { outlet14PDU2 2 }

current14PDU2 OBJECT-TYPE
SYNTAX INTEGER (0..65535)
ACCESS read-only
STATUS optional
DESCRIPTION
        " "
::= { outlet14PDU2 3 }

power14PDU2 OBJECT-TYPE
SYNTAX INTEGER (0..65535)
ACCESS read-only
STATUS optional
DESCRIPTION
        " "
::= { outlet14PDU2 4 }

pf14PDU2 OBJECT-TYPE
SYNTAX INTEGER (0..65535)
ACCESS read-only
STATUS optional
DESCRIPTION
        " "
::= { outlet14PDU2 5 }

energy14PDU2 OBJECT-TYPE
SYNTAX INTEGER (0..65535)
ACCESS read-only
STATUS optional
DESCRIPTION
        " "
::= { outlet14PDU2 6 }

switch15PDU2 OBJECT-TYPE
SYNTAX INTEGER (0..3)
ACCESS read-write
STATUS optional
DESCRIPTION
        " "
::= { outlet15PDU2 1 }

voltage15PDU2 OBJECT-TYPE
SYNTAX INTEGER (0..65535)
ACCESS read-only
STATUS optional
DESCRIPTION
        " "
::= { outlet15PDU2 2 }

current15PDU2 OBJECT-TYPE
SYNTAX INTEGER (0..65535)
ACCESS read-only
STATUS optional
DESCRIPTION
        " "
::= { outlet15PDU2 3 }

power15PDU2 OBJECT-TYPE
SYNTAX INTEGER (0..65535)
ACCESS read-only
STATUS optional
DESCRIPTION
        " "
::= { outlet15PDU2 4 }

pf15PDU2 OBJECT-TYPE
SYNTAX INTEGER (0..65535)
ACCESS read-only
STATUS optional
DESCRIPTION
        " "
::= { outlet15PDU2 5 }

energy15PDU2 OBJECT-TYPE
SYNTAX INTEGER (0..65535)
ACCESS read-only
STATUS optional
DESCRIPTION
        " "
::= { outlet15PDU2 6 }

switch16PDU2 OBJECT-TYPE
SYNTAX INTEGER (0..3)
ACCESS read-write
STATUS optional
DESCRIPTION
        " "
::= { outlet16PDU2 1 }

voltage16PDU2 OBJECT-TYPE
SYNTAX INTEGER (0..65535)
ACCESS read-only
STATUS optional
DESCRIPTION
        " "
::= { outlet16PDU2 2 }

current16PDU2 OBJECT-TYPE
SYNTAX INTEGER (0..65535)
ACCESS read-only
STATUS optional
DESCRIPTION
        " "
::= { outlet16PDU2 3 }

power16PDU2 OBJECT-TYPE
SYNTAX INTEGER (0..65535)
ACCESS read-only
STATUS optional
DESCRIPTION
        " "
::= { outlet16PDU2 4 }

pf16PDU2 OBJECT-TYPE
SYNTAX INTEGER (0..65535)
ACCESS read-only
STATUS optional
DESCRIPTION
        " "
::= { outlet16PDU2 5 }

energy16PDU2 OBJECT-TYPE
SYNTAX INTEGER (0..65535)
ACCESS read-only
STATUS optional
DESCRIPTION
        " "
::= { outlet16PDU2 6 }

switch17PDU2 OBJECT-TYPE
SYNTAX INTEGER (0..3)
ACCESS read-write
STATUS optional
DESCRIPTION
        " "
::= { outlet17PDU2 1 }

voltage17PDU2 OBJECT-TYPE
SYNTAX INTEGER (0..65535)
ACCESS read-only
STATUS optional
DESCRIPTION
        " "
::= { outlet17PDU2 2 }

current17PDU2 OBJECT-TYPE
SYNTAX INTEGER (0..65535)
ACCESS read-only
STATUS optional
DESCRIPTION
        " "
::= { outlet17PDU2 3 }

power17PDU2 OBJECT-TYPE
SYNTAX INTEGER (0..65535)
ACCESS read-only
STATUS optional
DESCRIPTION
        " "
::= { outlet17PDU2 4 }

pf17PDU2 OBJECT-TYPE
SYNTAX INTEGER (0..65535)
ACCESS read-only
STATUS optional
DESCRIPTION
        " "
::= { outlet17PDU2 5 }

energy17PDU2 OBJECT-TYPE
SYNTAX INTEGER (0..65535)
ACCESS read-only
STATUS optional
DESCRIPTION
        " "
::= { outlet17PDU2 6 }

switch18PDU2 OBJECT-TYPE
SYNTAX INTEGER (0..3)
ACCESS read-write
STATUS optional
DESCRIPTION
        " "
::= { outlet18PDU2 1 }

voltage18PDU2 OBJECT-TYPE
SYNTAX INTEGER (0..65535)
ACCESS read-only
STATUS optional
DESCRIPTION
        " "
::= { outlet18PDU2 2 }

current18PDU2 OBJECT-TYPE
SYNTAX INTEGER (0..65535)
ACCESS read-only
STATUS optional
DESCRIPTION
        " "
::= { outlet18PDU2 3 }

power18PDU2 OBJECT-TYPE
SYNTAX INTEGER (0..65535)
ACCESS read-only
STATUS optional
DESCRIPTION
        " "
::= { outlet18PDU2 4 }

pf18PDU2 OBJECT-TYPE
SYNTAX INTEGER (0..65535)
ACCESS read-only
STATUS optional
DESCRIPTION
        " "
::= { outlet18PDU2 5 }

energy18PDU2 OBJECT-TYPE
SYNTAX INTEGER (0..65535)
ACCESS read-only
STATUS optional
DESCRIPTION
        " "
::= { outlet18PDU2 6 }

switch19PDU2 OBJECT-TYPE
SYNTAX INTEGER (0..3)
ACCESS read-write
STATUS optional
DESCRIPTION
        " "
::= { outlet19PDU2 1 }

voltage19PDU2 OBJECT-TYPE
SYNTAX INTEGER (0..65535)
ACCESS read-only
STATUS optional
DESCRIPTION
        " "
::= { outlet19PDU2 2 }

current19PDU2 OBJECT-TYPE
SYNTAX INTEGER (0..65535)
ACCESS read-only
STATUS optional
DESCRIPTION
        " "
::= { outlet19PDU2 3 }

power19PDU2 OBJECT-TYPE
SYNTAX INTEGER (0..65535)
ACCESS read-only
STATUS optional
DESCRIPTION
        " "
::= { outlet19PDU2 4 }

pf19PDU2 OBJECT-TYPE
SYNTAX INTEGER (0..65535)
ACCESS read-only
STATUS optional
DESCRIPTION
        " "
::= { outlet19PDU2 5 }

energy19PDU2 OBJECT-TYPE
SYNTAX INTEGER (0..65535)
ACCESS read-only
STATUS optional
DESCRIPTION
        " "
::= { outlet19PDU2 6 }

switch20PDU2 OBJECT-TYPE
SYNTAX INTEGER (0..3)
ACCESS read-write
STATUS optional
DESCRIPTION
        " "
::= { outlet20PDU2 1 }

voltage20PDU2 OBJECT-TYPE
SYNTAX INTEGER (0..65535)
ACCESS read-only
STATUS optional
DESCRIPTION
        " "
::= { outlet20PDU2 2 }

current20PDU2 OBJECT-TYPE
SYNTAX INTEGER (0..65535)
ACCESS read-only
STATUS optional
DESCRIPTION
        " "
::= { outlet20PDU2 3 }

power20PDU2 OBJECT-TYPE
SYNTAX INTEGER (0..65535)
ACCESS read-only
STATUS optional
DESCRIPTION
        " "
::= { outlet20PDU2 4 }

pf20PDU2 OBJECT-TYPE
SYNTAX INTEGER (0..65535)
ACCESS read-only
STATUS optional
DESCRIPTION
        " "
::= { outlet20PDU2 5 }

energy20PDU2 OBJECT-TYPE
SYNTAX INTEGER (0..65535)
ACCESS read-only
STATUS optional
DESCRIPTION
        " "
::= { outlet20PDU2 6 }

switch21PDU2 OBJECT-TYPE
SYNTAX INTEGER (0..3)
ACCESS read-write
STATUS optional
DESCRIPTION
        " "
::= { outlet21PDU2 1 }

voltage21PDU2 OBJECT-TYPE
SYNTAX INTEGER (0..65535)
ACCESS read-only
STATUS optional
DESCRIPTION
        " "
::= { outlet21PDU2 2 }

current21PDU2 OBJECT-TYPE
SYNTAX INTEGER (0..65535)
ACCESS read-only
STATUS optional
DESCRIPTION
        " "
::= { outlet21PDU2 3 }

power21PDU2 OBJECT-TYPE
SYNTAX INTEGER (0..65535)
ACCESS read-only
STATUS optional
DESCRIPTION
        " "
::= { outlet21PDU2 4 }

pf21PDU2 OBJECT-TYPE
SYNTAX INTEGER (0..65535)
ACCESS read-only
STATUS optional
DESCRIPTION
        " "
::= { outlet21PDU2 5 }

energy21PDU2 OBJECT-TYPE
SYNTAX INTEGER (0..65535)
ACCESS read-only
STATUS optional
DESCRIPTION
        " "
::= { outlet21PDU2 6 }

switch22PDU2 OBJECT-TYPE
SYNTAX INTEGER (0..3)
ACCESS read-write
STATUS optional
DESCRIPTION
        " "
::= { outlet22PDU2 1 }

voltage22PDU2 OBJECT-TYPE
SYNTAX INTEGER (0..65535)
ACCESS read-only
STATUS optional
DESCRIPTION
        " "
::= { outlet22PDU2 2 }

current22PDU2 OBJECT-TYPE
SYNTAX INTEGER (0..65535)
ACCESS read-only
STATUS optional
DESCRIPTION
        " "
::= { outlet22PDU2 3 }

power22PDU2 OBJECT-TYPE
SYNTAX INTEGER (0..65535)
ACCESS read-only
STATUS optional
DESCRIPTION
        " "
::= { outlet22PDU2 4 }

pf22PDU2 OBJECT-TYPE
SYNTAX INTEGER (0..65535)
ACCESS read-only
STATUS optional
DESCRIPTION
        " "
::= { outlet22PDU2 5 }

energy22PDU2 OBJECT-TYPE
SYNTAX INTEGER (0..65535)
ACCESS read-only
STATUS optional
DESCRIPTION
        " "
::= { outlet22PDU2 6 }

switch23PDU2 OBJECT-TYPE
SYNTAX INTEGER (0..3)
ACCESS read-write
STATUS optional
DESCRIPTION
        " "
::= { outlet23PDU2 1 }

voltage23PDU2 OBJECT-TYPE
SYNTAX INTEGER (0..65535)
ACCESS read-only
STATUS optional
DESCRIPTION
        " "
::= { outlet23PDU2 2 }

current23PDU2 OBJECT-TYPE
SYNTAX INTEGER (0..65535)
ACCESS read-only
STATUS optional
DESCRIPTION
        " "
::= { outlet23PDU2 3 }

power23PDU2 OBJECT-TYPE
SYNTAX INTEGER (0..65535)
ACCESS read-only
STATUS optional
DESCRIPTION
        " "
::= { outlet23PDU2 4 }

pf23PDU2 OBJECT-TYPE
SYNTAX INTEGER (0..65535)
ACCESS read-only
STATUS optional
DESCRIPTION
        " "
::= { outlet23PDU2 5 }

energy23PDU2 OBJECT-TYPE
SYNTAX INTEGER (0..65535)
ACCESS read-only
STATUS optional
DESCRIPTION
        " "
::= { outlet23PDU2 6 }

switch24PDU2 OBJECT-TYPE
SYNTAX INTEGER (0..3)
ACCESS read-write
STATUS optional
DESCRIPTION
        " "
::= { outlet24PDU2 1 }

voltage24PDU2 OBJECT-TYPE
SYNTAX INTEGER (0..65535)
ACCESS read-only
STATUS optional
DESCRIPTION
        " "
::= { outlet24PDU2 2 }

current24PDU2 OBJECT-TYPE
SYNTAX INTEGER (0..65535)
ACCESS read-only
STATUS optional
DESCRIPTION
        " "
::= { outlet24PDU2 3 }

power24PDU2 OBJECT-TYPE
SYNTAX INTEGER (0..65535)
ACCESS read-only
STATUS optional
DESCRIPTION
        " "
::= { outlet24PDU2 4 }

pf24PDU2 OBJECT-TYPE
SYNTAX INTEGER (0..65535)
ACCESS read-only
STATUS optional
DESCRIPTION
        " "
::= { outlet24PDU2 5 }

energy24PDU2 OBJECT-TYPE
SYNTAX INTEGER (0..65535)
ACCESS read-only
STATUS optional
DESCRIPTION
        " "
::= { outlet24PDU2 6 }

switch25PDU2 OBJECT-TYPE
SYNTAX INTEGER (0..3)
ACCESS read-write
STATUS optional
DESCRIPTION
        " "
::= { outlet25PDU2 1 }

voltage25PDU2 OBJECT-TYPE
SYNTAX INTEGER (0..65535)
ACCESS read-only
STATUS optional
DESCRIPTION
        " "
::= { outlet25PDU2 2 }

current25PDU2 OBJECT-TYPE
SYNTAX INTEGER (0..65535)
ACCESS read-only
STATUS optional
DESCRIPTION
        " "
::= { outlet25PDU2 3 }

power25PDU2 OBJECT-TYPE
SYNTAX INTEGER (0..65535)
ACCESS read-only
STATUS optional
DESCRIPTION
        " "
::= { outlet25PDU2 4 }

pf25PDU2 OBJECT-TYPE
SYNTAX INTEGER (0..65535)
ACCESS read-only
STATUS optional
DESCRIPTION
        " "
::= { outlet25PDU2 5 }

energy25PDU2 OBJECT-TYPE
SYNTAX INTEGER (0..65535)
ACCESS read-only
STATUS optional
DESCRIPTION
        " "
::= { outlet25PDU2 6 }

switch26PDU2 OBJECT-TYPE
SYNTAX INTEGER (0..3)
ACCESS read-write
STATUS optional
DESCRIPTION
        " "
::= { outlet26PDU2 1 }

voltage26PDU2 OBJECT-TYPE
SYNTAX INTEGER (0..65535)
ACCESS read-only
STATUS optional
DESCRIPTION
        " "
::= { outlet26PDU2 2 }

current26PDU2 OBJECT-TYPE
SYNTAX INTEGER (0..65535)
ACCESS read-only
STATUS optional
DESCRIPTION
        " "
::= { outlet26PDU2 3 }

power26PDU2 OBJECT-TYPE
SYNTAX INTEGER (0..65535)
ACCESS read-only
STATUS optional
DESCRIPTION
        " "
::= { outlet26PDU2 4 }

pf26PDU2 OBJECT-TYPE
SYNTAX INTEGER (0..65535)
ACCESS read-only
STATUS optional
DESCRIPTION
        " "
::= { outlet26PDU2 5 }

energy26PDU2 OBJECT-TYPE
SYNTAX INTEGER (0..65535)
ACCESS read-only
STATUS optional
DESCRIPTION
        " "
::= { outlet26PDU2 6 }

switch27PDU2 OBJECT-TYPE
SYNTAX INTEGER (0..3)
ACCESS read-write
STATUS optional
DESCRIPTION
        " "
::= { outlet27PDU2 1 }

voltage27PDU2 OBJECT-TYPE
SYNTAX INTEGER (0..65535)
ACCESS read-only
STATUS optional
DESCRIPTION
        " "
::= { outlet27PDU2 2 }

current27PDU2 OBJECT-TYPE
SYNTAX INTEGER (0..65535)
ACCESS read-only
STATUS optional
DESCRIPTION
        " "
::= { outlet27PDU2 3 }

power27PDU2 OBJECT-TYPE
SYNTAX INTEGER (0..65535)
ACCESS read-only
STATUS optional
DESCRIPTION
        " "
::= { outlet27PDU2 4 }

pf27PDU2 OBJECT-TYPE
SYNTAX INTEGER (0..65535)
ACCESS read-only
STATUS optional
DESCRIPTION
        " "
::= { outlet27PDU2 5 }

energy27PDU2 OBJECT-TYPE
SYNTAX INTEGER (0..65535)
ACCESS read-only
STATUS optional
DESCRIPTION
        " "
::= { outlet27PDU2 6 }

switch28PDU2 OBJECT-TYPE
SYNTAX INTEGER (0..3)
ACCESS read-write
STATUS optional
DESCRIPTION
        " "
::= { outlet28PDU2 1 }

voltage28PDU2 OBJECT-TYPE
SYNTAX INTEGER (0..65535)
ACCESS read-only
STATUS optional
DESCRIPTION
        " "
::= { outlet28PDU2 2 }

current28PDU2 OBJECT-TYPE
SYNTAX INTEGER (0..65535)
ACCESS read-only
STATUS optional
DESCRIPTION
        " "
::= { outlet28PDU2 3 }

power28PDU2 OBJECT-TYPE
SYNTAX INTEGER (0..65535)
ACCESS read-only
STATUS optional
DESCRIPTION
        " "
::= { outlet28PDU2 4 }

pf28PDU2 OBJECT-TYPE
SYNTAX INTEGER (0..65535)
ACCESS read-only
STATUS optional
DESCRIPTION
        " "
::= { outlet28PDU2 5 }

energy28PDU2 OBJECT-TYPE
SYNTAX INTEGER (0..65535)
ACCESS read-only
STATUS optional
DESCRIPTION
        " "
::= { outlet28PDU2 6 }

switch29PDU2 OBJECT-TYPE
SYNTAX INTEGER (0..3)
ACCESS read-write
STATUS optional
DESCRIPTION
        " "
::= { outlet29PDU2 1 }

voltage29PDU2 OBJECT-TYPE
SYNTAX INTEGER (0..65535)
ACCESS read-only
STATUS optional
DESCRIPTION
        " "
::= { outlet29PDU2 2 }

current29PDU2 OBJECT-TYPE
SYNTAX INTEGER (0..65535)
ACCESS read-only
STATUS optional
DESCRIPTION
        " "
::= { outlet29PDU2 3 }

power29PDU2 OBJECT-TYPE
SYNTAX INTEGER (0..65535)
ACCESS read-only
STATUS optional
DESCRIPTION
        " "
::= { outlet29PDU2 4 }

pf29PDU2 OBJECT-TYPE
SYNTAX INTEGER (0..65535)
ACCESS read-only
STATUS optional
DESCRIPTION
        " "
::= { outlet29PDU2 5 }

energy29PDU2 OBJECT-TYPE
SYNTAX INTEGER (0..65535)
ACCESS read-only
STATUS optional
DESCRIPTION
        " "
::= { outlet29PDU2 6 }

switch30PDU2 OBJECT-TYPE
SYNTAX INTEGER (0..3)
ACCESS read-write
STATUS optional
DESCRIPTION
        " "
::= { outlet30PDU2 1 }

voltage30PDU2 OBJECT-TYPE
SYNTAX INTEGER (0..65535)
ACCESS read-only
STATUS optional
DESCRIPTION
        " "
::= { outlet30PDU2 2 }

current30PDU2 OBJECT-TYPE
SYNTAX INTEGER (0..65535)
ACCESS read-only
STATUS optional
DESCRIPTION
        " "
::= { outlet30PDU2 3 }

power30PDU2 OBJECT-TYPE
SYNTAX INTEGER (0..65535)
ACCESS read-only
STATUS optional
DESCRIPTION
        " "
::= { outlet30PDU2 4 }

pf30PDU2 OBJECT-TYPE
SYNTAX INTEGER (0..65535)
ACCESS read-only
STATUS optional
DESCRIPTION
        " "
::= { outlet30PDU2 5 }

energy30PDU2 OBJECT-TYPE
SYNTAX INTEGER (0..65535)
ACCESS read-only
STATUS optional
DESCRIPTION
        " "
::= { outlet30PDU2 6 }

switch31PDU2 OBJECT-TYPE
SYNTAX INTEGER (0..3)
ACCESS read-write
STATUS optional
DESCRIPTION
        " "
::= { outlet31PDU2 1 }

voltage31PDU2 OBJECT-TYPE
SYNTAX INTEGER (0..65535)
ACCESS read-only
STATUS optional
DESCRIPTION
        " "
::= { outlet31PDU2 2 }

current31PDU2 OBJECT-TYPE
SYNTAX INTEGER (0..65535)
ACCESS read-only
STATUS optional
DESCRIPTION
        " "
::= { outlet31PDU2 3 }

power31PDU2 OBJECT-TYPE
SYNTAX INTEGER (0..65535)
ACCESS read-only
STATUS optional
DESCRIPTION
        " "
::= { outlet31PDU2 4 }

pf31PDU2 OBJECT-TYPE
SYNTAX INTEGER (0..65535)
ACCESS read-only
STATUS optional
DESCRIPTION
        " "
::= { outlet31PDU2 5 }

energy31PDU2 OBJECT-TYPE
SYNTAX INTEGER (0..65535)
ACCESS read-only
STATUS optional
DESCRIPTION
        " "
::= { outlet31PDU2 6 }

switch32PDU2 OBJECT-TYPE
SYNTAX INTEGER (0..3)
ACCESS read-write
STATUS optional
DESCRIPTION
        " "
::= { outlet32PDU2 1 }

voltage32PDU2 OBJECT-TYPE
SYNTAX INTEGER (0..65535)
ACCESS read-only
STATUS optional
DESCRIPTION
        " "
::= { outlet32PDU2 2 }

current32PDU2 OBJECT-TYPE
SYNTAX INTEGER (0..65535)
ACCESS read-only
STATUS optional
DESCRIPTION
        " "
::= { outlet32PDU2 3 }

power32PDU2 OBJECT-TYPE
SYNTAX INTEGER (0..65535)
ACCESS read-only
STATUS optional
DESCRIPTION
        " "
::= { outlet32PDU2 4 }

pf32PDU2 OBJECT-TYPE
SYNTAX INTEGER (0..65535)
ACCESS read-only
STATUS optional
DESCRIPTION
        " "
::= { outlet32PDU2 5 }

energy32PDU2 OBJECT-TYPE
SYNTAX INTEGER (0..65535)
ACCESS read-only
STATUS optional
DESCRIPTION
        " "
::= { outlet32PDU2 6 }

switch33PDU2 OBJECT-TYPE
SYNTAX INTEGER (0..3)
ACCESS read-write
STATUS optional
DESCRIPTION
        " "
::= { outlet33PDU2 1 }

voltage33PDU2 OBJECT-TYPE
SYNTAX INTEGER (0..65535)
ACCESS read-only
STATUS optional
DESCRIPTION
        " "
::= { outlet33PDU2 2 }

current33PDU2 OBJECT-TYPE
SYNTAX INTEGER (0..65535)
ACCESS read-only
STATUS optional
DESCRIPTION
        " "
::= { outlet33PDU2 3 }

power33PDU2 OBJECT-TYPE
SYNTAX INTEGER (0..65535)
ACCESS read-only
STATUS optional
DESCRIPTION
        " "
::= { outlet33PDU2 4 }

pf33PDU2 OBJECT-TYPE
SYNTAX INTEGER (0..65535)
ACCESS read-only
STATUS optional
DESCRIPTION
        " "
::= { outlet33PDU2 5 }

energy33PDU2 OBJECT-TYPE
SYNTAX INTEGER (0..65535)
ACCESS read-only
STATUS optional
DESCRIPTION
        " "
::= { outlet33PDU2 6 }

switch34PDU2 OBJECT-TYPE
SYNTAX INTEGER (0..3)
ACCESS read-write
STATUS optional
DESCRIPTION
        " "
::= { outlet34PDU2 1 }

voltage34PDU2 OBJECT-TYPE
SYNTAX INTEGER (0..65535)
ACCESS read-only
STATUS optional
DESCRIPTION
        " "
::= { outlet34PDU2 2 }

current34PDU2 OBJECT-TYPE
SYNTAX INTEGER (0..65535)
ACCESS read-only
STATUS optional
DESCRIPTION
        " "
::= { outlet34PDU2 3 }

power34PDU2 OBJECT-TYPE
SYNTAX INTEGER (0..65535)
ACCESS read-only
STATUS optional
DESCRIPTION
        " "
::= { outlet34PDU2 4 }

pf34PDU2 OBJECT-TYPE
SYNTAX INTEGER (0..65535)
ACCESS read-only
STATUS optional
DESCRIPTION
        " "
::= { outlet34PDU2 5 }

energy34PDU2 OBJECT-TYPE
SYNTAX INTEGER (0..65535)
ACCESS read-only
STATUS optional
DESCRIPTION
        " "
::= { outlet34PDU2 6 }

switch35PDU2 OBJECT-TYPE
SYNTAX INTEGER (0..3)
ACCESS read-write
STATUS optional
DESCRIPTION
        " "
::= { outlet35PDU2 1 }

voltage35PDU2 OBJECT-TYPE
SYNTAX INTEGER (0..65535)
ACCESS read-only
STATUS optional
DESCRIPTION
        " "
::= { outlet35PDU2 2 }

current35PDU2 OBJECT-TYPE
SYNTAX INTEGER (0..65535)
ACCESS read-only
STATUS optional
DESCRIPTION
        " "
::= { outlet35PDU2 3 }

power35PDU2 OBJECT-TYPE
SYNTAX INTEGER (0..65535)
ACCESS read-only
STATUS optional
DESCRIPTION
        " "
::= { outlet35PDU2 4 }

pf35PDU2 OBJECT-TYPE
SYNTAX INTEGER (0..65535)
ACCESS read-only
STATUS optional
DESCRIPTION
        " "
::= { outlet35PDU2 5 }

energy35PDU2 OBJECT-TYPE
SYNTAX INTEGER (0..65535)
ACCESS read-only
STATUS optional
DESCRIPTION
        " "
::= { outlet35PDU2 6 }

switch36PDU2 OBJECT-TYPE
SYNTAX INTEGER (0..3)
ACCESS read-write
STATUS optional
DESCRIPTION
        " "
::= { outlet36PDU2 1 }

voltage36PDU2 OBJECT-TYPE
SYNTAX INTEGER (0..65535)
ACCESS read-only
STATUS optional
DESCRIPTION
        " "
::= { outlet36PDU2 2 }

current36PDU2 OBJECT-TYPE
SYNTAX INTEGER (0..65535)
ACCESS read-only
STATUS optional
DESCRIPTION
        " "
::= { outlet36PDU2 3 }

power36PDU2 OBJECT-TYPE
SYNTAX INTEGER (0..65535)
ACCESS read-only
STATUS optional
DESCRIPTION
        " "
::= { outlet36PDU2 4 }

pf36PDU2 OBJECT-TYPE
SYNTAX INTEGER (0..65535)
ACCESS read-only
STATUS optional
DESCRIPTION
        " "
::= { outlet36PDU2 5 }

energy36PDU2 OBJECT-TYPE
SYNTAX INTEGER (0..65535)
ACCESS read-only
STATUS optional
DESCRIPTION
        " "
::= { outlet36PDU2 6 }

sensor1 OBJECT IDENTIFIER ::= { pdu2 4 }

temperature1PDU2 OBJECT-TYPE
SYNTAX INTEGER (0..65535)
ACCESS read-only
STATUS optional
DESCRIPTION
        " "
::= { sensor1 1 }

humidity1PDU2 OBJECT-TYPE
SYNTAX INTEGER (0..65535)
ACCESS read-only
STATUS optional
DESCRIPTION
        " "
::= { sensor1 2 }

temperature2PDU2 OBJECT-TYPE
SYNTAX INTEGER (0..65535)
ACCESS read-only
STATUS optional
DESCRIPTION
        " "
::= { sensor1 3 }

humidity2PDU2 OBJECT-TYPE
SYNTAX INTEGER (0..65535)
ACCESS read-only
STATUS optional
DESCRIPTION
        " "
::= { sensor1 4 }

inputStatus1PDU2 OBJECT-TYPE
SYNTAX INTEGER (0..1)
ACCESS read-only
STATUS optional
DESCRIPTION
        " "
::= { sensor1 5 }

inputStatus2PDU2 OBJECT-TYPE
SYNTAX INTEGER (0..1)
ACCESS read-only
STATUS optional
DESCRIPTION
        " "
::= { sensor1 6 }

inputStatus3PDU2 OBJECT-TYPE
SYNTAX INTEGER (0..1)
ACCESS read-only
STATUS optional
DESCRIPTION
        " "
::= { sensor1 7 }

inputStatus4PDU2 OBJECT-TYPE
SYNTAX INTEGER (0..1)
ACCESS read-only
STATUS optional
DESCRIPTION
        " "
::= { sensor1 8 }

doStatus1PDU2 OBJECT-TYPE
SYNTAX INTEGER (0..1)
ACCESS read-only
STATUS optional
DESCRIPTION
        " "
::= { sensor1 9 }

doStatus2PDU2 OBJECT-TYPE
SYNTAX INTEGER (0..1)
ACCESS read-only
STATUS optional
DESCRIPTION
        " "
::= { sensor1 10 }

baseinfo1 OBJECT IDENTIFIER ::= { pdu3 1 }

cascadeAlarmPDU3 OBJECT-TYPE
SYNTAX INTEGER (0..3)
ACCESS read-only
STATUS optional
DESCRIPTION
        " "
::= { baseinfo1 1 }

deviceNamePDU3 OBJECT-TYPE
SYNTAX DisplayString (SIZE (32))
ACCESS read-write
STATUS optional
DESCRIPTION
        " "
::= { baseinfo1 2 }

outletNumberPDU3 OBJECT-TYPE
SYNTAX INTEGER (0..36)
ACCESS read-only
STATUS optional
DESCRIPTION
        " "
::= { baseinfo1 3 }

temphum1WarnStatPDU3 OBJECT-TYPE
SYNTAX INTEGER (0..127)
ACCESS read-only
STATUS optional
DESCRIPTION
        " "
::= { baseinfo1 4 }

temphum2WarnStatPDU3 OBJECT-TYPE
SYNTAX INTEGER (0..127)
ACCESS read-only
STATUS optional
DESCRIPTION
        " "
::= { baseinfo1 5 }

input1WarnStatPDU3 OBJECT-TYPE
SYNTAX INTEGER (0..1)
ACCESS read-only
STATUS optional
DESCRIPTION
        " "
::= { baseinfo1 6 }

input2WarnStatPDU3 OBJECT-TYPE
SYNTAX INTEGER (0..1)
ACCESS read-only
STATUS optional
DESCRIPTION
        " "
::= { baseinfo1 7 }

input3WarnStatPDU3 OBJECT-TYPE
SYNTAX INTEGER (0..1)
ACCESS read-only
STATUS optional
DESCRIPTION
        " "
::= { baseinfo1 8 }

input4WarnStatPDU3 OBJECT-TYPE
SYNTAX INTEGER (0..1)
ACCESS read-only
STATUS optional
DESCRIPTION
        " "
::= { baseinfo1 9 }

currentL1WarnStatPDU3 OBJECT-TYPE
SYNTAX INTEGER (0..127)
ACCESS read-only
STATUS optional
DESCRIPTION
        " "
::= { baseinfo1 10 }

currentL2WarnStatPDU3 OBJECT-TYPE
SYNTAX INTEGER (0..127)
ACCESS read-only
STATUS optional
DESCRIPTION
        " "
::= { baseinfo1 11 }

currentL3WarnStatPDU3 OBJECT-TYPE
SYNTAX INTEGER (0..127)
ACCESS read-only
STATUS optional
DESCRIPTION
        " "
::= { baseinfo1 12 }

voltageL1WarnStatPDU3 OBJECT-TYPE
SYNTAX INTEGER (0..127)
ACCESS read-only
STATUS optional
DESCRIPTION
        " "
::= { baseinfo1 13 }

voltageL2WarnStatPDU3 OBJECT-TYPE
SYNTAX INTEGER (0..127)
ACCESS read-only
STATUS optional
DESCRIPTION
        " "
::= { baseinfo1 14 }

voltageL3WarnStatPDU3 OBJECT-TYPE
SYNTAX INTEGER (0..127)
ACCESS read-only
STATUS optional
DESCRIPTION
        " "
::= { baseinfo1 15 }

outlet1WarnStatPDU3 OBJECT-TYPE
SYNTAX INTEGER (0..127)
ACCESS read-only
STATUS optional
DESCRIPTION
        " "
::= { baseinfo1 16 }

outlet2WarnStatPDU3 OBJECT-TYPE
SYNTAX INTEGER (0..127)
ACCESS read-only
STATUS optional
DESCRIPTION
        " "
::= { baseinfo1 17 }

outlet3WarnStatPDU3 OBJECT-TYPE
SYNTAX INTEGER (0..127)
ACCESS read-only
STATUS optional
DESCRIPTION
        " "
::= { baseinfo1 18 }

outlet4WarnStatPDU3 OBJECT-TYPE
SYNTAX INTEGER (0..127)
ACCESS read-only
STATUS optional
DESCRIPTION
        " "
::= { baseinfo1 19 }

outlet5WarnStatPDU3 OBJECT-TYPE
SYNTAX INTEGER (0..127)
ACCESS read-only
STATUS optional
DESCRIPTION
        " "
::= { baseinfo1 20 }

outlet6WarnStatPDU3 OBJECT-TYPE
SYNTAX INTEGER (0..127)
ACCESS read-only
STATUS optional
DESCRIPTION
        " "
::= { baseinfo1 21 }

outlet7WarnStatPDU3 OBJECT-TYPE
SYNTAX INTEGER (0..127)
ACCESS read-only
STATUS optional
DESCRIPTION
        " "
::= { baseinfo1 22 }

outlet8WarnStatPDU3 OBJECT-TYPE
SYNTAX INTEGER (0..127)
ACCESS read-only
STATUS optional
DESCRIPTION
        " "
::= { baseinfo1 23 }

outlet9WarnStatPDU3 OBJECT-TYPE
SYNTAX INTEGER (0..127)
ACCESS read-only
STATUS optional
DESCRIPTION
        " "
::= { baseinfo1 24 }

outlet10WarnStatPDU3 OBJECT-TYPE
SYNTAX INTEGER (0..127)
ACCESS read-only
STATUS optional
DESCRIPTION
        " "
::= { baseinfo1 25 }

outlet11WarnStatPDU3 OBJECT-TYPE
SYNTAX INTEGER (0..127)
ACCESS read-only
STATUS optional
DESCRIPTION
        " "
::= { baseinfo1 26 }

outlet12WarnStatPDU3 OBJECT-TYPE
SYNTAX INTEGER (0..127)
ACCESS read-only
STATUS optional
DESCRIPTION
        " "
::= { baseinfo1 27 }

outlet13WarnStatPDU3 OBJECT-TYPE
SYNTAX INTEGER (0..127)
ACCESS read-only
STATUS optional
DESCRIPTION
        " "
::= { baseinfo1 28 }

outlet14WarnStatPDU3 OBJECT-TYPE
SYNTAX INTEGER (0..127)
ACCESS read-only
STATUS optional
DESCRIPTION
        " "
::= { baseinfo1 29 }

outlet15WarnStatPDU3 OBJECT-TYPE
SYNTAX INTEGER (0..127)
ACCESS read-only
STATUS optional
DESCRIPTION
        " "
::= { baseinfo1 30 }

outlet16WarnStatPDU3 OBJECT-TYPE
SYNTAX INTEGER (0..127)
ACCESS read-only
STATUS optional
DESCRIPTION
        " "
::= { baseinfo1 31 }

outlet17WarnStatPDU3 OBJECT-TYPE
SYNTAX INTEGER (0..127)
ACCESS read-only
STATUS optional
DESCRIPTION
        " "
::= { baseinfo1 32 }

outlet18WarnStatPDU3 OBJECT-TYPE
SYNTAX INTEGER (0..127)
ACCESS read-only
STATUS optional
DESCRIPTION
        " "
::= { baseinfo1 33 }

outlet19WarnStatPDU3 OBJECT-TYPE
SYNTAX INTEGER (0..127)
ACCESS read-only
STATUS optional
DESCRIPTION
        " "
::= { baseinfo1 34 }

outlet20WarnStatPDU3 OBJECT-TYPE
SYNTAX INTEGER (0..127)
ACCESS read-only
STATUS optional
DESCRIPTION
        " "
::= { baseinfo1 35 }

outlet21WarnStatPDU3 OBJECT-TYPE
SYNTAX INTEGER (0..127)
ACCESS read-only
STATUS optional
DESCRIPTION
        " "
::= { baseinfo1 36 }

outlet22WarnStatPDU3 OBJECT-TYPE
SYNTAX INTEGER (0..127)
ACCESS read-only
STATUS optional
DESCRIPTION
        " "
::= { baseinfo1 37 }

outlet23WarnStatPDU3 OBJECT-TYPE
SYNTAX INTEGER (0..127)
ACCESS read-only
STATUS optional
DESCRIPTION
        " "
::= { baseinfo1 38 }

outlet24WarnStatPDU3 OBJECT-TYPE
SYNTAX INTEGER (0..127)
ACCESS read-only
STATUS optional
DESCRIPTION
        " "
::= { baseinfo1 39 }

outlet25WarnStatPDU3 OBJECT-TYPE
SYNTAX INTEGER (0..127)
ACCESS read-only
STATUS optional
DESCRIPTION
        " "
::= { baseinfo1 40 }

outlet26WarnStatPDU3 OBJECT-TYPE
SYNTAX INTEGER (0..127)
ACCESS read-only
STATUS optional
DESCRIPTION
        " "
::= { baseinfo1 41 }

outlet27WarnStatPDU3 OBJECT-TYPE
SYNTAX INTEGER (0..127)
ACCESS read-only
STATUS optional
DESCRIPTION
        " "
::= { baseinfo1 42 }

outlet28WarnStatPDU3 OBJECT-TYPE
SYNTAX INTEGER (0..127)
ACCESS read-only
STATUS optional
DESCRIPTION
        " "
::= { baseinfo1 43 }

outlet29WarnStatPDU3 OBJECT-TYPE
SYNTAX INTEGER (0..127)
ACCESS read-only
STATUS optional
DESCRIPTION
        " "
::= { baseinfo1 44 }

outlet30WarnStatPDU3 OBJECT-TYPE
SYNTAX INTEGER (0..127)
ACCESS read-only
STATUS optional
DESCRIPTION
        " "
::= { baseinfo1 45 }

outlet31WarnStatPDU3 OBJECT-TYPE
SYNTAX INTEGER (0..127)
ACCESS read-only
STATUS optional
DESCRIPTION
        " "
::= { baseinfo1 46 }

outlet32WarnStatPDU3 OBJECT-TYPE
SYNTAX INTEGER (0..127)
ACCESS read-only
STATUS optional
DESCRIPTION
        " "
::= { baseinfo1 47 }

outlet33WarnStatPDU3 OBJECT-TYPE
SYNTAX INTEGER (0..127)
ACCESS read-only
STATUS optional
DESCRIPTION
        " "
::= { baseinfo1 48 }

outlet34WarnStatPDU3 OBJECT-TYPE
SYNTAX INTEGER (0..127)
ACCESS read-only
STATUS optional
DESCRIPTION
        " "
::= { baseinfo1 49 }

outlet35WarnStatPDU3 OBJECT-TYPE
SYNTAX INTEGER (0..127)
ACCESS read-only
STATUS optional
DESCRIPTION
        " "
::= { baseinfo1 50 }

outlet36WarnStatPDU3 OBJECT-TYPE
SYNTAX INTEGER (0..127)
ACCESS read-only
STATUS optional
DESCRIPTION
        " "
::= { baseinfo1 51 }

input1 OBJECT IDENTIFIER ::= { pdu3 2 }

currentL1PDU3 OBJECT-TYPE
SYNTAX INTEGER (0..65535)
ACCESS read-only
STATUS optional
DESCRIPTION
        " "
::= { input1 1 }

voltageL1PDU3 OBJECT-TYPE
SYNTAX INTEGER (0..65535)
ACCESS read-only
STATUS optional
DESCRIPTION
        " "
::= { input1 2 }

powerL1PDU3 OBJECT-TYPE
SYNTAX INTEGER (0..65535)
ACCESS read-only
STATUS optional
DESCRIPTION
        " "
::= { input1 3 }

pfL1PDU3 OBJECT-TYPE
SYNTAX INTEGER (0..65535)
ACCESS read-only
STATUS optional
DESCRIPTION
        " "
::= { input1 4 }

energyL1PDU3 OBJECT-TYPE
SYNTAX INTEGER (0..65535)
ACCESS read-only
STATUS optional
DESCRIPTION
        " "
::= { input1 5 }

currentL2PDU3 OBJECT-TYPE
SYNTAX INTEGER (0..65535)
ACCESS read-only
STATUS optional
DESCRIPTION
        " "
::= { input1 6 }

voltageL2PDU3 OBJECT-TYPE
SYNTAX INTEGER (0..65535)
ACCESS read-only
STATUS optional
DESCRIPTION
        " "
::= { input1 7 }

powerL2PDU3 OBJECT-TYPE
SYNTAX INTEGER (0..65535)
ACCESS read-only
STATUS optional
DESCRIPTION
        " "
::= { input1 8 }

pfL2PDU3 OBJECT-TYPE
SYNTAX INTEGER (0..65535)
ACCESS read-only
STATUS optional
DESCRIPTION
        " "
::= { input1 9 }

energyL2PDU3 OBJECT-TYPE
SYNTAX INTEGER (0..65535)
ACCESS read-only
STATUS optional
DESCRIPTION
        " "
::= { input1 10 }

currentL3PDU3 OBJECT-TYPE
SYNTAX INTEGER (0..65535)
ACCESS read-only
STATUS optional
DESCRIPTION
        " "
::= { input1 11 }

voltageL3PDU3 OBJECT-TYPE
SYNTAX INTEGER (0..65535)
ACCESS read-only
STATUS optional
DESCRIPTION
        " "
::= { input1 12 }

powerL3PDU3 OBJECT-TYPE
SYNTAX INTEGER (0..65535)
ACCESS read-only
STATUS optional
DESCRIPTION
        " "
::= { input1 13 }

pfL3PDU3 OBJECT-TYPE
SYNTAX INTEGER (0..65535)
ACCESS read-only
STATUS optional
DESCRIPTION
        " "
::= { input1 14 }

energyL3PDU3 OBJECT-TYPE
SYNTAX INTEGER (0..65535)
ACCESS read-only
STATUS optional
DESCRIPTION
        " "
::= { input1 15 }

outletinfo1 OBJECT IDENTIFIER ::= { pdu3 3 }

outlet1PDU3 OBJECT IDENTIFIER ::= { outletinfo1 1 }

outlet2PDU3 OBJECT IDENTIFIER ::= { outletinfo1 2 }

outlet3PDU3 OBJECT IDENTIFIER ::= { outletinfo1 3 }

outlet4PDU3 OBJECT IDENTIFIER ::= { outletinfo1 4 }

outlet5PDU3 OBJECT IDENTIFIER ::= { outletinfo1 5 }

outlet6PDU3 OBJECT IDENTIFIER ::= { outletinfo1 6 }

outlet7PDU3 OBJECT IDENTIFIER ::= { outletinfo1 7 }

outlet8PDU3 OBJECT IDENTIFIER ::= { outletinfo1 8 }

outlet9PDU3 OBJECT IDENTIFIER ::= { outletinfo1 9 }

outlet10PDU3 OBJECT IDENTIFIER ::= { outletinfo1 10 }

outlet11PDU3 OBJECT IDENTIFIER ::= { outletinfo1 11 }

outlet12PDU3 OBJECT IDENTIFIER ::= { outletinfo1 12 }

outlet13PDU3 OBJECT IDENTIFIER ::= { outletinfo1 13 }

outlet14PDU3 OBJECT IDENTIFIER ::= { outletinfo1 14 }

outlet15PDU3 OBJECT IDENTIFIER ::= { outletinfo1 15 }

outlet16PDU3 OBJECT IDENTIFIER ::= { outletinfo1 16 }

outlet17PDU3 OBJECT IDENTIFIER ::= { outletinfo1 17 }

outlet18PDU3 OBJECT IDENTIFIER ::= { outletinfo1 18 }

outlet19PDU3 OBJECT IDENTIFIER ::= { outletinfo1 19 }

outlet20PDU3 OBJECT IDENTIFIER ::= { outletinfo1 20 }

outlet21PDU3 OBJECT IDENTIFIER ::= { outletinfo1 21 }

outlet22PDU3 OBJECT IDENTIFIER ::= { outletinfo1 22 }

outlet23PDU3 OBJECT IDENTIFIER ::= { outletinfo1 23 }

outlet24PDU3 OBJECT IDENTIFIER ::= { outletinfo1 24 }

outlet25PDU3 OBJECT IDENTIFIER ::= { outletinfo1 25 }

outlet26PDU3 OBJECT IDENTIFIER ::= { outletinfo1 26 }

outlet27PDU3 OBJECT IDENTIFIER ::= { outletinfo1 27 }

outlet28PDU3 OBJECT IDENTIFIER ::= { outletinfo1 28 }

outlet29PDU3 OBJECT IDENTIFIER ::= { outletinfo1 29 }

outlet30PDU3 OBJECT IDENTIFIER ::= { outletinfo1 30 }

outlet31PDU3 OBJECT IDENTIFIER ::= { outletinfo1 31 }

outlet32PDU3 OBJECT IDENTIFIER ::= { outletinfo1 32 }

outlet33PDU3 OBJECT IDENTIFIER ::= { outletinfo1 33 }

outlet34PDU3 OBJECT IDENTIFIER ::= { outletinfo1 34 }

outlet35PDU3 OBJECT IDENTIFIER ::= { outletinfo1 35 }

outlet36PDU3 OBJECT IDENTIFIER ::= { outletinfo1 36 }

switch1PDU3 OBJECT-TYPE
SYNTAX INTEGER (0..3)
ACCESS read-write
STATUS optional
DESCRIPTION
        " "
::= { outlet1PDU3 1 }

voltage1PDU3 OBJECT-TYPE
SYNTAX INTEGER (0..65535)
ACCESS read-only
STATUS optional
DESCRIPTION
        " "
::= { outlet1PDU3 2 }

current1PDU3 OBJECT-TYPE
SYNTAX INTEGER (0..65535)
ACCESS read-only
STATUS optional
DESCRIPTION
        " "
::= { outlet1PDU3 3 }

power1PDU3 OBJECT-TYPE
SYNTAX INTEGER (0..65535)
ACCESS read-only
STATUS optional
DESCRIPTION
        " "
::= { outlet1PDU3 4 }

pf1PDU3 OBJECT-TYPE
SYNTAX INTEGER (0..65535)
ACCESS read-only
STATUS optional
DESCRIPTION
        " "
::= { outlet1PDU3 5 }

energy1PDU3 OBJECT-TYPE
SYNTAX INTEGER (0..65535)
ACCESS read-only
STATUS optional
DESCRIPTION
        " "
::= { outlet1PDU3 6 }

switch2PDU3 OBJECT-TYPE
SYNTAX INTEGER (0..3)
ACCESS read-write
STATUS optional
DESCRIPTION
        " "
::= { outlet2PDU3 1 }

voltage2PDU3 OBJECT-TYPE
SYNTAX INTEGER (0..65535)
ACCESS read-only
STATUS optional
DESCRIPTION
        " "
::= { outlet2PDU3 2 }

current2PDU3 OBJECT-TYPE
SYNTAX INTEGER (0..65535)
ACCESS read-only
STATUS optional
DESCRIPTION
        " "
::= { outlet2PDU3 3 }

power2PDU3 OBJECT-TYPE
SYNTAX INTEGER (0..65535)
ACCESS read-only
STATUS optional
DESCRIPTION
        " "
::= { outlet2PDU3 4 }

pf2PDU3 OBJECT-TYPE
SYNTAX INTEGER (0..65535)
ACCESS read-only
STATUS optional
DESCRIPTION
        " "
::= { outlet2PDU3 5 }

energy2PDU3 OBJECT-TYPE
SYNTAX INTEGER (0..65535)
ACCESS read-only
STATUS optional
DESCRIPTION
        " "
::= { outlet2PDU3 6 }

switch3PDU3 OBJECT-TYPE
SYNTAX INTEGER (0..3)
ACCESS read-write
STATUS optional
DESCRIPTION
        " "
::= { outlet3PDU3 1 }

voltage3PDU3 OBJECT-TYPE
SYNTAX INTEGER (0..65535)
ACCESS read-only
STATUS optional
DESCRIPTION
        " "
::= { outlet3PDU3 2 }

current3PDU3 OBJECT-TYPE
SYNTAX INTEGER (0..65535)
ACCESS read-only
STATUS optional
DESCRIPTION
        " "
::= { outlet3PDU3 3 }

power3PDU3 OBJECT-TYPE
SYNTAX INTEGER (0..65535)
ACCESS read-only
STATUS optional
DESCRIPTION
        " "
::= { outlet3PDU3 4 }

pf3PDU3 OBJECT-TYPE
SYNTAX INTEGER (0..65535)
ACCESS read-only
STATUS optional
DESCRIPTION
        " "
::= { outlet3PDU3 5 }

energy3PDU3 OBJECT-TYPE
SYNTAX INTEGER (0..65535)
ACCESS read-only
STATUS optional
DESCRIPTION
        " "
::= { outlet3PDU3 6 }

switch4PDU3 OBJECT-TYPE
SYNTAX INTEGER (0..3)
ACCESS read-write
STATUS optional
DESCRIPTION
        " "
::= { outlet4PDU3 1 }

voltage4PDU3 OBJECT-TYPE
SYNTAX INTEGER (0..65535)
ACCESS read-only
STATUS optional
DESCRIPTION
        " "
::= { outlet4PDU3 2 }

current4PDU3 OBJECT-TYPE
SYNTAX INTEGER (0..65535)
ACCESS read-only
STATUS optional
DESCRIPTION
        " "
::= { outlet4PDU3 3 }

power4PDU3 OBJECT-TYPE
SYNTAX INTEGER (0..65535)
ACCESS read-only
STATUS optional
DESCRIPTION
        " "
::= { outlet4PDU3 4 }

pf4PDU3 OBJECT-TYPE
SYNTAX INTEGER (0..65535)
ACCESS read-only
STATUS optional
DESCRIPTION
        " "
::= { outlet4PDU3 5 }

energy4PDU3 OBJECT-TYPE
SYNTAX INTEGER (0..65535)
ACCESS read-only
STATUS optional
DESCRIPTION
        " "
::= { outlet4PDU3 6 }

switch5PDU3 OBJECT-TYPE
SYNTAX INTEGER (0..3)
ACCESS read-write
STATUS optional
DESCRIPTION
        " "
::= { outlet5PDU3 1 }

voltage5PDU3 OBJECT-TYPE
SYNTAX INTEGER (0..65535)
ACCESS read-only
STATUS optional
DESCRIPTION
        " "
::= { outlet5PDU3 2 }

current5PDU3 OBJECT-TYPE
SYNTAX INTEGER (0..65535)
ACCESS read-only
STATUS optional
DESCRIPTION
        " "
::= { outlet5PDU3 3 }

power5PDU3 OBJECT-TYPE
SYNTAX INTEGER (0..65535)
ACCESS read-only
STATUS optional
DESCRIPTION
        " "
::= { outlet5PDU3 4 }

pf5PDU3 OBJECT-TYPE
SYNTAX INTEGER (0..65535)
ACCESS read-only
STATUS optional
DESCRIPTION
        " "
::= { outlet5PDU3 5 }

energy5PDU3 OBJECT-TYPE
SYNTAX INTEGER (0..65535)
ACCESS read-only
STATUS optional
DESCRIPTION
        " "
::= { outlet5PDU3 6 }

switch6PDU3 OBJECT-TYPE
SYNTAX INTEGER (0..3)
ACCESS read-write
STATUS optional
DESCRIPTION
        " "
::= { outlet6PDU3 1 }

voltage6PDU3 OBJECT-TYPE
SYNTAX INTEGER (0..65535)
ACCESS read-only
STATUS optional
DESCRIPTION
        " "
::= { outlet6PDU3 2 }

current6PDU3 OBJECT-TYPE
SYNTAX INTEGER (0..65535)
ACCESS read-only
STATUS optional
DESCRIPTION
        " "
::= { outlet6PDU3 3 }

power6PDU3 OBJECT-TYPE
SYNTAX INTEGER (0..65535)
ACCESS read-only
STATUS optional
DESCRIPTION
        " "
::= { outlet6PDU3 4 }

pf6PDU3 OBJECT-TYPE
SYNTAX INTEGER (0..65535)
ACCESS read-only
STATUS optional
DESCRIPTION
        " "
::= { outlet6PDU3 5 }

energy6PDU3 OBJECT-TYPE
SYNTAX INTEGER (0..65535)
ACCESS read-only
STATUS optional
DESCRIPTION
        " "
::= { outlet6PDU3 6 }

switch7PDU3 OBJECT-TYPE
SYNTAX INTEGER (0..3)
ACCESS read-write
STATUS optional
DESCRIPTION
        " "
::= { outlet7PDU3 1 }

voltage7PDU3 OBJECT-TYPE
SYNTAX INTEGER (0..65535)
ACCESS read-only
STATUS optional
DESCRIPTION
        " "
::= { outlet7PDU3 2 }

current7PDU3 OBJECT-TYPE
SYNTAX INTEGER (0..65535)
ACCESS read-only
STATUS optional
DESCRIPTION
        " "
::= { outlet7PDU3 3 }

power7PDU3 OBJECT-TYPE
SYNTAX INTEGER (0..65535)
ACCESS read-only
STATUS optional
DESCRIPTION
        " "
::= { outlet7PDU3 4 }

pf7PDU3 OBJECT-TYPE
SYNTAX INTEGER (0..65535)
ACCESS read-only
STATUS optional
DESCRIPTION
        " "
::= { outlet7PDU3 5 }

energy7PDU3 OBJECT-TYPE
SYNTAX INTEGER (0..65535)
ACCESS read-only
STATUS optional
DESCRIPTION
        " "
::= { outlet7PDU3 6 }

switch8PDU3 OBJECT-TYPE
SYNTAX INTEGER (0..3)
ACCESS read-write
STATUS optional
DESCRIPTION
        " "
::= { outlet8PDU3 1 }

voltage8PDU3 OBJECT-TYPE
SYNTAX INTEGER (0..65535)
ACCESS read-only
STATUS optional
DESCRIPTION
        " "
::= { outlet8PDU3 2 }

current8PDU3 OBJECT-TYPE
SYNTAX INTEGER (0..65535)
ACCESS read-only
STATUS optional
DESCRIPTION
        " "
::= { outlet8PDU3 3 }

power8PDU3 OBJECT-TYPE
SYNTAX INTEGER (0..65535)
ACCESS read-only
STATUS optional
DESCRIPTION
        " "
::= { outlet8PDU3 4 }

pf8PDU3 OBJECT-TYPE
SYNTAX INTEGER (0..65535)
ACCESS read-only
STATUS optional
DESCRIPTION
        " "
::= { outlet8PDU3 5 }

energy8PDU3 OBJECT-TYPE
SYNTAX INTEGER (0..65535)
ACCESS read-only
STATUS optional
DESCRIPTION
        " "
::= { outlet8PDU3 6 }

switch9PDU3 OBJECT-TYPE
SYNTAX INTEGER (0..3)
ACCESS read-write
STATUS optional
DESCRIPTION
        " "
::= { outlet9PDU3 1 }

voltage9PDU3 OBJECT-TYPE
SYNTAX INTEGER (0..65535)
ACCESS read-only
STATUS optional
DESCRIPTION
        " "
::= { outlet9PDU3 2 }

current9PDU3 OBJECT-TYPE
SYNTAX INTEGER (0..65535)
ACCESS read-only
STATUS optional
DESCRIPTION
        " "
::= { outlet9PDU3 3 }

power9PDU3 OBJECT-TYPE
SYNTAX INTEGER (0..65535)
ACCESS read-only
STATUS optional
DESCRIPTION
        " "
::= { outlet9PDU3 4 }

pf9PDU3 OBJECT-TYPE
SYNTAX INTEGER (0..65535)
ACCESS read-only
STATUS optional
DESCRIPTION
        " "
::= { outlet9PDU3 5 }

energy9PDU3 OBJECT-TYPE
SYNTAX INTEGER (0..65535)
ACCESS read-only
STATUS optional
DESCRIPTION
        " "
::= { outlet9PDU3 6 }

switch10PDU3 OBJECT-TYPE
SYNTAX INTEGER (0..3)
ACCESS read-write
STATUS optional
DESCRIPTION
        " "
::= { outlet10PDU3 1 }

voltage10PDU3 OBJECT-TYPE
SYNTAX INTEGER (0..65535)
ACCESS read-only
STATUS optional
DESCRIPTION
        " "
::= { outlet10PDU3 2 }

current10PDU3 OBJECT-TYPE
SYNTAX INTEGER (0..65535)
ACCESS read-only
STATUS optional
DESCRIPTION
        " "
::= { outlet10PDU3 3 }

power10PDU3 OBJECT-TYPE
SYNTAX INTEGER (0..65535)
ACCESS read-only
STATUS optional
DESCRIPTION
        " "
::= { outlet10PDU3 4 }

pf10PDU3 OBJECT-TYPE
SYNTAX INTEGER (0..65535)
ACCESS read-only
STATUS optional
DESCRIPTION
        " "
::= { outlet10PDU3 5 }

energy10PDU3 OBJECT-TYPE
SYNTAX INTEGER (0..65535)
ACCESS read-only
STATUS optional
DESCRIPTION
        " "
::= { outlet10PDU3 6 }

switch11PDU3 OBJECT-TYPE
SYNTAX INTEGER (0..3)
ACCESS read-write
STATUS optional
DESCRIPTION
        " "
::= { outlet11PDU3 1 }

voltage11PDU3 OBJECT-TYPE
SYNTAX INTEGER (0..65535)
ACCESS read-only
STATUS optional
DESCRIPTION
        " "
::= { outlet11PDU3 2 }

current11PDU3 OBJECT-TYPE
SYNTAX INTEGER (0..65535)
ACCESS read-only
STATUS optional
DESCRIPTION
        " "
::= { outlet11PDU3 3 }

power11PDU3 OBJECT-TYPE
SYNTAX INTEGER (0..65535)
ACCESS read-only
STATUS optional
DESCRIPTION
        " "
::= { outlet11PDU3 4 }

pf11PDU3 OBJECT-TYPE
SYNTAX INTEGER (0..65535)
ACCESS read-only
STATUS optional
DESCRIPTION
        " "
::= { outlet11PDU3 5 }

energy11PDU3 OBJECT-TYPE
SYNTAX INTEGER (0..65535)
ACCESS read-only
STATUS optional
DESCRIPTION
        " "
::= { outlet11PDU3 6 }

switch12PDU3 OBJECT-TYPE
SYNTAX INTEGER (0..3)
ACCESS read-write
STATUS optional
DESCRIPTION
        " "
::= { outlet12PDU3 1 }

voltage12PDU3 OBJECT-TYPE
SYNTAX INTEGER (0..65535)
ACCESS read-only
STATUS optional
DESCRIPTION
        " "
::= { outlet12PDU3 2 }

current12PDU3 OBJECT-TYPE
SYNTAX INTEGER (0..65535)
ACCESS read-only
STATUS optional
DESCRIPTION
        " "
::= { outlet12PDU3 3 }

power12PDU3 OBJECT-TYPE
SYNTAX INTEGER (0..65535)
ACCESS read-only
STATUS optional
DESCRIPTION
        " "
::= { outlet12PDU3 4 }

pf12PDU3 OBJECT-TYPE
SYNTAX INTEGER (0..65535)
ACCESS read-only
STATUS optional
DESCRIPTION
        " "
::= { outlet12PDU3 5 }

energy12PDU3 OBJECT-TYPE
SYNTAX INTEGER (0..65535)
ACCESS read-only
STATUS optional
DESCRIPTION
        " "
::= { outlet12PDU3 6 }

switch13PDU3 OBJECT-TYPE
SYNTAX INTEGER (0..3)
ACCESS read-write
STATUS optional
DESCRIPTION
        " "
::= { outlet13PDU3 1 }

voltage13PDU3 OBJECT-TYPE
SYNTAX INTEGER (0..65535)
ACCESS read-only
STATUS optional
DESCRIPTION
        " "
::= { outlet13PDU3 2 }

current13PDU3 OBJECT-TYPE
SYNTAX INTEGER (0..65535)
ACCESS read-only
STATUS optional
DESCRIPTION
        " "
::= { outlet13PDU3 3 }

power13PDU3 OBJECT-TYPE
SYNTAX INTEGER (0..65535)
ACCESS read-only
STATUS optional
DESCRIPTION
        " "
::= { outlet13PDU3 4 }

pf13PDU3 OBJECT-TYPE
SYNTAX INTEGER (0..65535)
ACCESS read-only
STATUS optional
DESCRIPTION
        " "
::= { outlet13PDU3 5 }

energy13PDU3 OBJECT-TYPE
SYNTAX INTEGER (0..65535)
ACCESS read-only
STATUS optional
DESCRIPTION
        " "
::= { outlet13PDU3 6 }

switch14PDU3 OBJECT-TYPE
SYNTAX INTEGER (0..3)
ACCESS read-write
STATUS optional
DESCRIPTION
        " "
::= { outlet14PDU3 1 }

voltage14PDU3 OBJECT-TYPE
SYNTAX INTEGER (0..65535)
ACCESS read-only
STATUS optional
DESCRIPTION
        " "
::= { outlet14PDU3 2 }

current14PDU3 OBJECT-TYPE
SYNTAX INTEGER (0..65535)
ACCESS read-only
STATUS optional
DESCRIPTION
        " "
::= { outlet14PDU3 3 }

power14PDU3 OBJECT-TYPE
SYNTAX INTEGER (0..65535)
ACCESS read-only
STATUS optional
DESCRIPTION
        " "
::= { outlet14PDU3 4 }

pf14PDU3 OBJECT-TYPE
SYNTAX INTEGER (0..65535)
ACCESS read-only
STATUS optional
DESCRIPTION
        " "
::= { outlet14PDU3 5 }

energy14PDU3 OBJECT-TYPE
SYNTAX INTEGER (0..65535)
ACCESS read-only
STATUS optional
DESCRIPTION
        " "
::= { outlet14PDU3 6 }

switch15PDU3 OBJECT-TYPE
SYNTAX INTEGER (0..3)
ACCESS read-write
STATUS optional
DESCRIPTION
        " "
::= { outlet15PDU3 1 }

voltage15PDU3 OBJECT-TYPE
SYNTAX INTEGER (0..65535)
ACCESS read-only
STATUS optional
DESCRIPTION
        " "
::= { outlet15PDU3 2 }

current15PDU3 OBJECT-TYPE
SYNTAX INTEGER (0..65535)
ACCESS read-only
STATUS optional
DESCRIPTION
        " "
::= { outlet15PDU3 3 }

power15PDU3 OBJECT-TYPE
SYNTAX INTEGER (0..65535)
ACCESS read-only
STATUS optional
DESCRIPTION
        " "
::= { outlet15PDU3 4 }

pf15PDU3 OBJECT-TYPE
SYNTAX INTEGER (0..65535)
ACCESS read-only
STATUS optional
DESCRIPTION
        " "
::= { outlet15PDU3 5 }

energy15PDU3 OBJECT-TYPE
SYNTAX INTEGER (0..65535)
ACCESS read-only
STATUS optional
DESCRIPTION
        " "
::= { outlet15PDU3 6 }

switch16PDU3 OBJECT-TYPE
SYNTAX INTEGER (0..3)
ACCESS read-write
STATUS optional
DESCRIPTION
        " "
::= { outlet16PDU3 1 }

voltage16PDU3 OBJECT-TYPE
SYNTAX INTEGER (0..65535)
ACCESS read-only
STATUS optional
DESCRIPTION
        " "
::= { outlet16PDU3 2 }

current16PDU3 OBJECT-TYPE
SYNTAX INTEGER (0..65535)
ACCESS read-only
STATUS optional
DESCRIPTION
        " "
::= { outlet16PDU3 3 }

power16PDU3 OBJECT-TYPE
SYNTAX INTEGER (0..65535)
ACCESS read-only
STATUS optional
DESCRIPTION
        " "
::= { outlet16PDU3 4 }

pf16PDU3 OBJECT-TYPE
SYNTAX INTEGER (0..65535)
ACCESS read-only
STATUS optional
DESCRIPTION
        " "
::= { outlet16PDU3 5 }

energy16PDU3 OBJECT-TYPE
SYNTAX INTEGER (0..65535)
ACCESS read-only
STATUS optional
DESCRIPTION
        " "
::= { outlet16PDU3 6 }

switch17PDU3 OBJECT-TYPE
SYNTAX INTEGER (0..3)
ACCESS read-write
STATUS optional
DESCRIPTION
        " "
::= { outlet17PDU3 1 }

voltage17PDU3 OBJECT-TYPE
SYNTAX INTEGER (0..65535)
ACCESS read-only
STATUS optional
DESCRIPTION
        " "
::= { outlet17PDU3 2 }

current17PDU3 OBJECT-TYPE
SYNTAX INTEGER (0..65535)
ACCESS read-only
STATUS optional
DESCRIPTION
        " "
::= { outlet17PDU3 3 }

power17PDU3 OBJECT-TYPE
SYNTAX INTEGER (0..65535)
ACCESS read-only
STATUS optional
DESCRIPTION
        " "
::= { outlet17PDU3 4 }

pf17PDU3 OBJECT-TYPE
SYNTAX INTEGER (0..65535)
ACCESS read-only
STATUS optional
DESCRIPTION
        " "
::= { outlet17PDU3 5 }

energy17PDU3 OBJECT-TYPE
SYNTAX INTEGER (0..65535)
ACCESS read-only
STATUS optional
DESCRIPTION
        " "
::= { outlet17PDU3 6 }

switch18PDU3 OBJECT-TYPE
SYNTAX INTEGER (0..3)
ACCESS read-write
STATUS optional
DESCRIPTION
        " "
::= { outlet18PDU3 1 }

voltage18PDU3 OBJECT-TYPE
SYNTAX INTEGER (0..65535)
ACCESS read-only
STATUS optional
DESCRIPTION
        " "
::= { outlet18PDU3 2 }

current18PDU3 OBJECT-TYPE
SYNTAX INTEGER (0..65535)
ACCESS read-only
STATUS optional
DESCRIPTION
        " "
::= { outlet18PDU3 3 }

power18PDU3 OBJECT-TYPE
SYNTAX INTEGER (0..65535)
ACCESS read-only
STATUS optional
DESCRIPTION
        " "
::= { outlet18PDU3 4 }

pf18PDU3 OBJECT-TYPE
SYNTAX INTEGER (0..65535)
ACCESS read-only
STATUS optional
DESCRIPTION
        " "
::= { outlet18PDU3 5 }

energy18PDU3 OBJECT-TYPE
SYNTAX INTEGER (0..65535)
ACCESS read-only
STATUS optional
DESCRIPTION
        " "
::= { outlet18PDU3 6 }

switch19PDU3 OBJECT-TYPE
SYNTAX INTEGER (0..3)
ACCESS read-write
STATUS optional
DESCRIPTION
        " "
::= { outlet19PDU3 1 }

voltage19PDU3 OBJECT-TYPE
SYNTAX INTEGER (0..65535)
ACCESS read-only
STATUS optional
DESCRIPTION
        " "
::= { outlet19PDU3 2 }

current19PDU3 OBJECT-TYPE
SYNTAX INTEGER (0..65535)
ACCESS read-only
STATUS optional
DESCRIPTION
        " "
::= { outlet19PDU3 3 }

power19PDU3 OBJECT-TYPE
SYNTAX INTEGER (0..65535)
ACCESS read-only
STATUS optional
DESCRIPTION
        " "
::= { outlet19PDU3 4 }

pf19PDU3 OBJECT-TYPE
SYNTAX INTEGER (0..65535)
ACCESS read-only
STATUS optional
DESCRIPTION
        " "
::= { outlet19PDU3 5 }

energy19PDU3 OBJECT-TYPE
SYNTAX INTEGER (0..65535)
ACCESS read-only
STATUS optional
DESCRIPTION
        " "
::= { outlet19PDU3 6 }

switch20PDU3 OBJECT-TYPE
SYNTAX INTEGER (0..3)
ACCESS read-write
STATUS optional
DESCRIPTION
        " "
::= { outlet20PDU3 1 }

voltage20PDU3 OBJECT-TYPE
SYNTAX INTEGER (0..65535)
ACCESS read-only
STATUS optional
DESCRIPTION
        " "
::= { outlet20PDU3 2 }

current20PDU3 OBJECT-TYPE
SYNTAX INTEGER (0..65535)
ACCESS read-only
STATUS optional
DESCRIPTION
        " "
::= { outlet20PDU3 3 }

power20PDU3 OBJECT-TYPE
SYNTAX INTEGER (0..65535)
ACCESS read-only
STATUS optional
DESCRIPTION
        " "
::= { outlet20PDU3 4 }

pf20PDU3 OBJECT-TYPE
SYNTAX INTEGER (0..65535)
ACCESS read-only
STATUS optional
DESCRIPTION
        " "
::= { outlet20PDU3 5 }

energy20PDU3 OBJECT-TYPE
SYNTAX INTEGER (0..65535)
ACCESS read-only
STATUS optional
DESCRIPTION
        " "
::= { outlet20PDU3 6 }

switch21PDU3 OBJECT-TYPE
SYNTAX INTEGER (0..3)
ACCESS read-write
STATUS optional
DESCRIPTION
        " "
::= { outlet21PDU3 1 }

voltage21PDU3 OBJECT-TYPE
SYNTAX INTEGER (0..65535)
ACCESS read-only
STATUS optional
DESCRIPTION
        " "
::= { outlet21PDU3 2 }

current21PDU3 OBJECT-TYPE
SYNTAX INTEGER (0..65535)
ACCESS read-only
STATUS optional
DESCRIPTION
        " "
::= { outlet21PDU3 3 }

power21PDU3 OBJECT-TYPE
SYNTAX INTEGER (0..65535)
ACCESS read-only
STATUS optional
DESCRIPTION
        " "
::= { outlet21PDU3 4 }

pf21PDU3 OBJECT-TYPE
SYNTAX INTEGER (0..65535)
ACCESS read-only
STATUS optional
DESCRIPTION
        " "
::= { outlet21PDU3 5 }

energy21PDU3 OBJECT-TYPE
SYNTAX INTEGER (0..65535)
ACCESS read-only
STATUS optional
DESCRIPTION
        " "
::= { outlet21PDU3 6 }

switch22PDU3 OBJECT-TYPE
SYNTAX INTEGER (0..3)
ACCESS read-write
STATUS optional
DESCRIPTION
        " "
::= { outlet22PDU3 1 }

voltage22PDU3 OBJECT-TYPE
SYNTAX INTEGER (0..65535)
ACCESS read-only
STATUS optional
DESCRIPTION
        " "
::= { outlet22PDU3 2 }

current22PDU3 OBJECT-TYPE
SYNTAX INTEGER (0..65535)
ACCESS read-only
STATUS optional
DESCRIPTION
        " "
::= { outlet22PDU3 3 }

power22PDU3 OBJECT-TYPE
SYNTAX INTEGER (0..65535)
ACCESS read-only
STATUS optional
DESCRIPTION
        " "
::= { outlet22PDU3 4 }

pf22PDU3 OBJECT-TYPE
SYNTAX INTEGER (0..65535)
ACCESS read-only
STATUS optional
DESCRIPTION
        " "
::= { outlet22PDU3 5 }

energy22PDU3 OBJECT-TYPE
SYNTAX INTEGER (0..65535)
ACCESS read-only
STATUS optional
DESCRIPTION
        " "
::= { outlet22PDU3 6 }

switch23PDU3 OBJECT-TYPE
SYNTAX INTEGER (0..3)
ACCESS read-write
STATUS optional
DESCRIPTION
        " "
::= { outlet23PDU3 1 }

voltage23PDU3 OBJECT-TYPE
SYNTAX INTEGER (0..65535)
ACCESS read-only
STATUS optional
DESCRIPTION
        " "
::= { outlet23PDU3 2 }

current23PDU3 OBJECT-TYPE
SYNTAX INTEGER (0..65535)
ACCESS read-only
STATUS optional
DESCRIPTION
        " "
::= { outlet23PDU3 3 }

power23PDU3 OBJECT-TYPE
SYNTAX INTEGER (0..65535)
ACCESS read-only
STATUS optional
DESCRIPTION
        " "
::= { outlet23PDU3 4 }

pf23PDU3 OBJECT-TYPE
SYNTAX INTEGER (0..65535)
ACCESS read-only
STATUS optional
DESCRIPTION
        " "
::= { outlet23PDU3 5 }

energy23PDU3 OBJECT-TYPE
SYNTAX INTEGER (0..65535)
ACCESS read-only
STATUS optional
DESCRIPTION
        " "
::= { outlet23PDU3 6 }

switch24PDU3 OBJECT-TYPE
SYNTAX INTEGER (0..3)
ACCESS read-write
STATUS optional
DESCRIPTION
        " "
::= { outlet24PDU3 1 }

voltage24PDU3 OBJECT-TYPE
SYNTAX INTEGER (0..65535)
ACCESS read-only
STATUS optional
DESCRIPTION
        " "
::= { outlet24PDU3 2 }

current24PDU3 OBJECT-TYPE
SYNTAX INTEGER (0..65535)
ACCESS read-only
STATUS optional
DESCRIPTION
        " "
::= { outlet24PDU3 3 }

power24PDU3 OBJECT-TYPE
SYNTAX INTEGER (0..65535)
ACCESS read-only
STATUS optional
DESCRIPTION
        " "
::= { outlet24PDU3 4 }

pf24PDU3 OBJECT-TYPE
SYNTAX INTEGER (0..65535)
ACCESS read-only
STATUS optional
DESCRIPTION
        " "
::= { outlet24PDU3 5 }

energy24PDU3 OBJECT-TYPE
SYNTAX INTEGER (0..65535)
ACCESS read-only
STATUS optional
DESCRIPTION
        " "
::= { outlet24PDU3 6 }

switch25PDU3 OBJECT-TYPE
SYNTAX INTEGER (0..3)
ACCESS read-write
STATUS optional
DESCRIPTION
        " "
::= { outlet25PDU3 1 }

voltage25PDU3 OBJECT-TYPE
SYNTAX INTEGER (0..65535)
ACCESS read-only
STATUS optional
DESCRIPTION
        " "
::= { outlet25PDU3 2 }

current25PDU3 OBJECT-TYPE
SYNTAX INTEGER (0..65535)
ACCESS read-only
STATUS optional
DESCRIPTION
        " "
::= { outlet25PDU3 3 }

power25PDU3 OBJECT-TYPE
SYNTAX INTEGER (0..65535)
ACCESS read-only
STATUS optional
DESCRIPTION
        " "
::= { outlet25PDU3 4 }

pf25PDU3 OBJECT-TYPE
SYNTAX INTEGER (0..65535)
ACCESS read-only
STATUS optional
DESCRIPTION
        " "
::= { outlet25PDU3 5 }

energy25PDU3 OBJECT-TYPE
SYNTAX INTEGER (0..65535)
ACCESS read-only
STATUS optional
DESCRIPTION
        " "
::= { outlet25PDU3 6 }

switch26PDU3 OBJECT-TYPE
SYNTAX INTEGER (0..3)
ACCESS read-write
STATUS optional
DESCRIPTION
        " "
::= { outlet26PDU3 1 }

voltage26PDU3 OBJECT-TYPE
SYNTAX INTEGER (0..65535)
ACCESS read-only
STATUS optional
DESCRIPTION
        " "
::= { outlet26PDU3 2 }

current26PDU3 OBJECT-TYPE
SYNTAX INTEGER (0..65535)
ACCESS read-only
STATUS optional
DESCRIPTION
        " "
::= { outlet26PDU3 3 }

power26PDU3 OBJECT-TYPE
SYNTAX INTEGER (0..65535)
ACCESS read-only
STATUS optional
DESCRIPTION
        " "
::= { outlet26PDU3 4 }

pf26PDU3 OBJECT-TYPE
SYNTAX INTEGER (0..65535)
ACCESS read-only
STATUS optional
DESCRIPTION
        " "
::= { outlet26PDU3 5 }

energy26PDU3 OBJECT-TYPE
SYNTAX INTEGER (0..65535)
ACCESS read-only
STATUS optional
DESCRIPTION
        " "
::= { outlet26PDU3 6 }

switch27PDU3 OBJECT-TYPE
SYNTAX INTEGER (0..3)
ACCESS read-write
STATUS optional
DESCRIPTION
        " "
::= { outlet27PDU3 1 }

voltage27PDU3 OBJECT-TYPE
SYNTAX INTEGER (0..65535)
ACCESS read-only
STATUS optional
DESCRIPTION
        " "
::= { outlet27PDU3 2 }

current27PDU3 OBJECT-TYPE
SYNTAX INTEGER (0..65535)
ACCESS read-only
STATUS optional
DESCRIPTION
        " "
::= { outlet27PDU3 3 }

power27PDU3 OBJECT-TYPE
SYNTAX INTEGER (0..65535)
ACCESS read-only
STATUS optional
DESCRIPTION
        " "
::= { outlet27PDU3 4 }

pf27PDU3 OBJECT-TYPE
SYNTAX INTEGER (0..65535)
ACCESS read-only
STATUS optional
DESCRIPTION
        " "
::= { outlet27PDU3 5 }

energy27PDU3 OBJECT-TYPE
SYNTAX INTEGER (0..65535)
ACCESS read-only
STATUS optional
DESCRIPTION
        " "
::= { outlet27PDU3 6 }

switch28PDU3 OBJECT-TYPE
SYNTAX INTEGER (0..3)
ACCESS read-write
STATUS optional
DESCRIPTION
        " "
::= { outlet28PDU3 1 }

voltage28PDU3 OBJECT-TYPE
SYNTAX INTEGER (0..65535)
ACCESS read-only
STATUS optional
DESCRIPTION
        " "
::= { outlet28PDU3 2 }

current28PDU3 OBJECT-TYPE
SYNTAX INTEGER (0..65535)
ACCESS read-only
STATUS optional
DESCRIPTION
        " "
::= { outlet28PDU3 3 }

power28PDU3 OBJECT-TYPE
SYNTAX INTEGER (0..65535)
ACCESS read-only
STATUS optional
DESCRIPTION
        " "
::= { outlet28PDU3 4 }

pf28PDU3 OBJECT-TYPE
SYNTAX INTEGER (0..65535)
ACCESS read-only
STATUS optional
DESCRIPTION
        " "
::= { outlet28PDU3 5 }

energy28PDU3 OBJECT-TYPE
SYNTAX INTEGER (0..65535)
ACCESS read-only
STATUS optional
DESCRIPTION
        " "
::= { outlet28PDU3 6 }

switch29PDU3 OBJECT-TYPE
SYNTAX INTEGER (0..3)
ACCESS read-write
STATUS optional
DESCRIPTION
        " "
::= { outlet29PDU3 1 }

voltage29PDU3 OBJECT-TYPE
SYNTAX INTEGER (0..65535)
ACCESS read-only
STATUS optional
DESCRIPTION
        " "
::= { outlet29PDU3 2 }

current29PDU3 OBJECT-TYPE
SYNTAX INTEGER (0..65535)
ACCESS read-only
STATUS optional
DESCRIPTION
        " "
::= { outlet29PDU3 3 }

power29PDU3 OBJECT-TYPE
SYNTAX INTEGER (0..65535)
ACCESS read-only
STATUS optional
DESCRIPTION
        " "
::= { outlet29PDU3 4 }

pf29PDU3 OBJECT-TYPE
SYNTAX INTEGER (0..65535)
ACCESS read-only
STATUS optional
DESCRIPTION
        " "
::= { outlet29PDU3 5 }

energy29PDU3 OBJECT-TYPE
SYNTAX INTEGER (0..65535)
ACCESS read-only
STATUS optional
DESCRIPTION
        " "
::= { outlet29PDU3 6 }

switch30PDU3 OBJECT-TYPE
SYNTAX INTEGER (0..3)
ACCESS read-write
STATUS optional
DESCRIPTION
        " "
::= { outlet30PDU3 1 }

voltage30PDU3 OBJECT-TYPE
SYNTAX INTEGER (0..65535)
ACCESS read-only
STATUS optional
DESCRIPTION
        " "
::= { outlet30PDU3 2 }

current30PDU3 OBJECT-TYPE
SYNTAX INTEGER (0..65535)
ACCESS read-only
STATUS optional
DESCRIPTION
        " "
::= { outlet30PDU3 3 }

power30PDU3 OBJECT-TYPE
SYNTAX INTEGER (0..65535)
ACCESS read-only
STATUS optional
DESCRIPTION
        " "
::= { outlet30PDU3 4 }

pf30PDU3 OBJECT-TYPE
SYNTAX INTEGER (0..65535)
ACCESS read-only
STATUS optional
DESCRIPTION
        " "
::= { outlet30PDU3 5 }

energy30PDU3 OBJECT-TYPE
SYNTAX INTEGER (0..65535)
ACCESS read-only
STATUS optional
DESCRIPTION
        " "
::= { outlet30PDU3 6 }

switch31PDU3 OBJECT-TYPE
SYNTAX INTEGER (0..3)
ACCESS read-write
STATUS optional
DESCRIPTION
        " "
::= { outlet31PDU3 1 }

voltage31PDU3 OBJECT-TYPE
SYNTAX INTEGER (0..65535)
ACCESS read-only
STATUS optional
DESCRIPTION
        " "
::= { outlet31PDU3 2 }

current31PDU3 OBJECT-TYPE
SYNTAX INTEGER (0..65535)
ACCESS read-only
STATUS optional
DESCRIPTION
        " "
::= { outlet31PDU3 3 }

power31PDU3 OBJECT-TYPE
SYNTAX INTEGER (0..65535)
ACCESS read-only
STATUS optional
DESCRIPTION
        " "
::= { outlet31PDU3 4 }

pf31PDU3 OBJECT-TYPE
SYNTAX INTEGER (0..65535)
ACCESS read-only
STATUS optional
DESCRIPTION
        " "
::= { outlet31PDU3 5 }

energy31PDU3 OBJECT-TYPE
SYNTAX INTEGER (0..65535)
ACCESS read-only
STATUS optional
DESCRIPTION
        " "
::= { outlet31PDU3 6 }

switch32PDU3 OBJECT-TYPE
SYNTAX INTEGER (0..3)
ACCESS read-write
STATUS optional
DESCRIPTION
        " "
::= { outlet32PDU3 1 }

voltage32PDU3 OBJECT-TYPE
SYNTAX INTEGER (0..65535)
ACCESS read-only
STATUS optional
DESCRIPTION
        " "
::= { outlet32PDU3 2 }

current32PDU3 OBJECT-TYPE
SYNTAX INTEGER (0..65535)
ACCESS read-only
STATUS optional
DESCRIPTION
        " "
::= { outlet32PDU3 3 }

power32PDU3 OBJECT-TYPE
SYNTAX INTEGER (0..65535)
ACCESS read-only
STATUS optional
DESCRIPTION
        " "
::= { outlet32PDU3 4 }

pf32PDU3 OBJECT-TYPE
SYNTAX INTEGER (0..65535)
ACCESS read-only
STATUS optional
DESCRIPTION
        " "
::= { outlet32PDU3 5 }

energy32PDU3 OBJECT-TYPE
SYNTAX INTEGER (0..65535)
ACCESS read-only
STATUS optional
DESCRIPTION
        " "
::= { outlet32PDU3 6 }

switch33PDU3 OBJECT-TYPE
SYNTAX INTEGER (0..3)
ACCESS read-write
STATUS optional
DESCRIPTION
        " "
::= { outlet33PDU3 1 }

voltage33PDU3 OBJECT-TYPE
SYNTAX INTEGER (0..65535)
ACCESS read-only
STATUS optional
DESCRIPTION
        " "
::= { outlet33PDU3 2 }

current33PDU3 OBJECT-TYPE
SYNTAX INTEGER (0..65535)
ACCESS read-only
STATUS optional
DESCRIPTION
        " "
::= { outlet33PDU3 3 }

power33PDU3 OBJECT-TYPE
SYNTAX INTEGER (0..65535)
ACCESS read-only
STATUS optional
DESCRIPTION
        " "
::= { outlet33PDU3 4 }

pf33PDU3 OBJECT-TYPE
SYNTAX INTEGER (0..65535)
ACCESS read-only
STATUS optional
DESCRIPTION
        " "
::= { outlet33PDU3 5 }

energy33PDU3 OBJECT-TYPE
SYNTAX INTEGER (0..65535)
ACCESS read-only
STATUS optional
DESCRIPTION
        " "
::= { outlet33PDU3 6 }

switch34PDU3 OBJECT-TYPE
SYNTAX INTEGER (0..3)
ACCESS read-write
STATUS optional
DESCRIPTION
        " "
::= { outlet34PDU3 1 }

voltage34PDU3 OBJECT-TYPE
SYNTAX INTEGER (0..65535)
ACCESS read-only
STATUS optional
DESCRIPTION
        " "
::= { outlet34PDU3 2 }

current34PDU3 OBJECT-TYPE
SYNTAX INTEGER (0..65535)
ACCESS read-only
STATUS optional
DESCRIPTION
        " "
::= { outlet34PDU3 3 }

power34PDU3 OBJECT-TYPE
SYNTAX INTEGER (0..65535)
ACCESS read-only
STATUS optional
DESCRIPTION
        " "
::= { outlet34PDU3 4 }

pf34PDU3 OBJECT-TYPE
SYNTAX INTEGER (0..65535)
ACCESS read-only
STATUS optional
DESCRIPTION
        " "
::= { outlet34PDU3 5 }

energy34PDU3 OBJECT-TYPE
SYNTAX INTEGER (0..65535)
ACCESS read-only
STATUS optional
DESCRIPTION
        " "
::= { outlet34PDU3 6 }

switch35PDU3 OBJECT-TYPE
SYNTAX INTEGER (0..3)
ACCESS read-write
STATUS optional
DESCRIPTION
        " "
::= { outlet35PDU3 1 }

voltage35PDU3 OBJECT-TYPE
SYNTAX INTEGER (0..65535)
ACCESS read-only
STATUS optional
DESCRIPTION
        " "
::= { outlet35PDU3 2 }

current35PDU3 OBJECT-TYPE
SYNTAX INTEGER (0..65535)
ACCESS read-only
STATUS optional
DESCRIPTION
        " "
::= { outlet35PDU3 3 }

power35PDU3 OBJECT-TYPE
SYNTAX INTEGER (0..65535)
ACCESS read-only
STATUS optional
DESCRIPTION
        " "
::= { outlet35PDU3 4 }

pf35PDU3 OBJECT-TYPE
SYNTAX INTEGER (0..65535)
ACCESS read-only
STATUS optional
DESCRIPTION
        " "
::= { outlet35PDU3 5 }

energy35PDU3 OBJECT-TYPE
SYNTAX INTEGER (0..65535)
ACCESS read-only
STATUS optional
DESCRIPTION
        " "
::= { outlet35PDU3 6 }

switch36PDU3 OBJECT-TYPE
SYNTAX INTEGER (0..3)
ACCESS read-write
STATUS optional
DESCRIPTION
        " "
::= { outlet36PDU3 1 }

voltage36PDU3 OBJECT-TYPE
SYNTAX INTEGER (0..65535)
ACCESS read-only
STATUS optional
DESCRIPTION
        " "
::= { outlet36PDU3 2 }

current36PDU3 OBJECT-TYPE
SYNTAX INTEGER (0..65535)
ACCESS read-only
STATUS optional
DESCRIPTION
        " "
::= { outlet36PDU3 3 }

power36PDU3 OBJECT-TYPE
SYNTAX INTEGER (0..65535)
ACCESS read-only
STATUS optional
DESCRIPTION
        " "
::= { outlet36PDU3 4 }

pf36PDU3 OBJECT-TYPE
SYNTAX INTEGER (0..65535)
ACCESS read-only
STATUS optional
DESCRIPTION
        " "
::= { outlet36PDU3 5 }

energy36PDU3 OBJECT-TYPE
SYNTAX INTEGER (0..65535)
ACCESS read-only
STATUS optional
DESCRIPTION
        " "
::= { outlet36PDU3 6 }

sensor1 OBJECT IDENTIFIER ::= { pdu3 4 }

temperature1PDU3 OBJECT-TYPE
SYNTAX INTEGER (0..65535)
ACCESS read-only
STATUS optional
DESCRIPTION
        " "
::= { sensor1 1 }

humidity1PDU3 OBJECT-TYPE
SYNTAX INTEGER (0..65535)
ACCESS read-only
STATUS optional
DESCRIPTION
        " "
::= { sensor1 2 }

temperature2PDU3 OBJECT-TYPE
SYNTAX INTEGER (0..65535)
ACCESS read-only
STATUS optional
DESCRIPTION
        " "
::= { sensor1 3 }

humidity2PDU3 OBJECT-TYPE
SYNTAX INTEGER (0..65535)
ACCESS read-only
STATUS optional
DESCRIPTION
        " "
::= { sensor1 4 }

inputStatus1PDU3 OBJECT-TYPE
SYNTAX INTEGER (0..1)
ACCESS read-only
STATUS optional
DESCRIPTION
        " "
::= { sensor1 5 }

inputStatus2PDU3 OBJECT-TYPE
SYNTAX INTEGER (0..1)
ACCESS read-only
STATUS optional
DESCRIPTION
        " "
::= { sensor1 6 }

inputStatus3PDU3 OBJECT-TYPE
SYNTAX INTEGER (0..1)
ACCESS read-only
STATUS optional
DESCRIPTION
        " "
::= { sensor1 7 }

inputStatus4PDU3 OBJECT-TYPE
SYNTAX INTEGER (0..1)
ACCESS read-only
STATUS optional
DESCRIPTION
        " "
::= { sensor1 8 }

doStatus1PDU3 OBJECT-TYPE
SYNTAX INTEGER (0..1)
ACCESS read-only
STATUS optional
DESCRIPTION
        " "
::= { sensor1 9 }

doStatus2PDU3 OBJECT-TYPE
SYNTAX INTEGER (0..1)
ACCESS read-only
STATUS optional
DESCRIPTION
        " "
::= { sensor1 10 }

baseinfo1 OBJECT IDENTIFIER ::= { pdu4 1 }

cascadeAlarmPDU4 OBJECT-TYPE
SYNTAX INTEGER (0..3)
ACCESS read-only
STATUS optional
DESCRIPTION
        " "
::= { baseinfo1 1 }

deviceNamePDU4 OBJECT-TYPE
SYNTAX DisplayString (SIZE (32))
ACCESS read-write
STATUS optional
DESCRIPTION
        " "
::= { baseinfo1 2 }

outletNumberPDU4 OBJECT-TYPE
SYNTAX INTEGER (0..36)
ACCESS read-only
STATUS optional
DESCRIPTION
        " "
::= { baseinfo1 3 }

temphum1WarnStatPDU4 OBJECT-TYPE
SYNTAX INTEGER (0..127)
ACCESS read-only
STATUS optional
DESCRIPTION
        " "
::= { baseinfo1 4 }

temphum2WarnStatPDU4 OBJECT-TYPE
SYNTAX INTEGER (0..127)
ACCESS read-only
STATUS optional
DESCRIPTION
        " "
::= { baseinfo1 5 }

input1WarnStatPDU4 OBJECT-TYPE
SYNTAX INTEGER (0..1)
ACCESS read-only
STATUS optional
DESCRIPTION
        " "
::= { baseinfo1 6 }

input2WarnStatPDU4 OBJECT-TYPE
SYNTAX INTEGER (0..1)
ACCESS read-only
STATUS optional
DESCRIPTION
        " "
::= { baseinfo1 7 }

input3WarnStatPDU4 OBJECT-TYPE
SYNTAX INTEGER (0..1)
ACCESS read-only
STATUS optional
DESCRIPTION
        " "
::= { baseinfo1 8 }

input4WarnStatPDU4 OBJECT-TYPE
SYNTAX INTEGER (0..1)
ACCESS read-only
STATUS optional
DESCRIPTION
        " "
::= { baseinfo1 9 }

currentL1WarnStatPDU4 OBJECT-TYPE
SYNTAX INTEGER (0..127)
ACCESS read-only
STATUS optional
DESCRIPTION
        " "
::= { baseinfo1 10 }

currentL2WarnStatPDU4 OBJECT-TYPE
SYNTAX INTEGER (0..127)
ACCESS read-only
STATUS optional
DESCRIPTION
        " "
::= { baseinfo1 11 }

currentL3WarnStatPDU4 OBJECT-TYPE
SYNTAX INTEGER (0..127)
ACCESS read-only
STATUS optional
DESCRIPTION
        " "
::= { baseinfo1 12 }

voltageL1WarnStatPDU4 OBJECT-TYPE
SYNTAX INTEGER (0..127)
ACCESS read-only
STATUS optional
DESCRIPTION
        " "
::= { baseinfo1 13 }

voltageL2WarnStatPDU4 OBJECT-TYPE
SYNTAX INTEGER (0..127)
ACCESS read-only
STATUS optional
DESCRIPTION
        " "
::= { baseinfo1 14 }

voltageL3WarnStatPDU4 OBJECT-TYPE
SYNTAX INTEGER (0..127)
ACCESS read-only
STATUS optional
DESCRIPTION
        " "
::= { baseinfo1 15 }

outlet1WarnStatPDU4 OBJECT-TYPE
SYNTAX INTEGER (0..127)
ACCESS read-only
STATUS optional
DESCRIPTION
        " "
::= { baseinfo1 16 }

outlet2WarnStatPDU4 OBJECT-TYPE
SYNTAX INTEGER (0..127)
ACCESS read-only
STATUS optional
DESCRIPTION
        " "
::= { baseinfo1 17 }

outlet3WarnStatPDU4 OBJECT-TYPE
SYNTAX INTEGER (0..127)
ACCESS read-only
STATUS optional
DESCRIPTION
        " "
::= { baseinfo1 18 }

outlet4WarnStatPDU4 OBJECT-TYPE
SYNTAX INTEGER (0..127)
ACCESS read-only
STATUS optional
DESCRIPTION
        " "
::= { baseinfo1 19 }

outlet5WarnStatPDU4 OBJECT-TYPE
SYNTAX INTEGER (0..127)
ACCESS read-only
STATUS optional
DESCRIPTION
        " "
::= { baseinfo1 20 }

outlet6WarnStatPDU4 OBJECT-TYPE
SYNTAX INTEGER (0..127)
ACCESS read-only
STATUS optional
DESCRIPTION
        " "
::= { baseinfo1 21 }

outlet7WarnStatPDU4 OBJECT-TYPE
SYNTAX INTEGER (0..127)
ACCESS read-only
STATUS optional
DESCRIPTION
        " "
::= { baseinfo1 22 }

outlet8WarnStatPDU4 OBJECT-TYPE
SYNTAX INTEGER (0..127)
ACCESS read-only
STATUS optional
DESCRIPTION
        " "
::= { baseinfo1 23 }

outlet9WarnStatPDU4 OBJECT-TYPE
SYNTAX INTEGER (0..127)
ACCESS read-only
STATUS optional
DESCRIPTION
        " "
::= { baseinfo1 24 }

outlet10WarnStatPDU4 OBJECT-TYPE
SYNTAX INTEGER (0..127)
ACCESS read-only
STATUS optional
DESCRIPTION
        " "
::= { baseinfo1 25 }

outlet11WarnStatPDU4 OBJECT-TYPE
SYNTAX INTEGER (0..127)
ACCESS read-only
STATUS optional
DESCRIPTION
        " "
::= { baseinfo1 26 }

outlet12WarnStatPDU4 OBJECT-TYPE
SYNTAX INTEGER (0..127)
ACCESS read-only
STATUS optional
DESCRIPTION
        " "
::= { baseinfo1 27 }

outlet13WarnStatPDU4 OBJECT-TYPE
SYNTAX INTEGER (0..127)
ACCESS read-only
STATUS optional
DESCRIPTION
        " "
::= { baseinfo1 28 }

outlet14WarnStatPDU4 OBJECT-TYPE
SYNTAX INTEGER (0..127)
ACCESS read-only
STATUS optional
DESCRIPTION
        " "
::= { baseinfo1 29 }

outlet15WarnStatPDU4 OBJECT-TYPE
SYNTAX INTEGER (0..127)
ACCESS read-only
STATUS optional
DESCRIPTION
        " "
::= { baseinfo1 30 }

outlet16WarnStatPDU4 OBJECT-TYPE
SYNTAX INTEGER (0..127)
ACCESS read-only
STATUS optional
DESCRIPTION
        " "
::= { baseinfo1 31 }

outlet17WarnStatPDU4 OBJECT-TYPE
SYNTAX INTEGER (0..127)
ACCESS read-only
STATUS optional
DESCRIPTION
        " "
::= { baseinfo1 32 }

outlet18WarnStatPDU4 OBJECT-TYPE
SYNTAX INTEGER (0..127)
ACCESS read-only
STATUS optional
DESCRIPTION
        " "
::= { baseinfo1 33 }

outlet19WarnStatPDU4 OBJECT-TYPE
SYNTAX INTEGER (0..127)
ACCESS read-only
STATUS optional
DESCRIPTION
        " "
::= { baseinfo1 34 }

outlet20WarnStatPDU4 OBJECT-TYPE
SYNTAX INTEGER (0..127)
ACCESS read-only
STATUS optional
DESCRIPTION
        " "
::= { baseinfo1 35 }

outlet21WarnStatPDU4 OBJECT-TYPE
SYNTAX INTEGER (0..127)
ACCESS read-only
STATUS optional
DESCRIPTION
        " "
::= { baseinfo1 36 }

outlet22WarnStatPDU4 OBJECT-TYPE
SYNTAX INTEGER (0..127)
ACCESS read-only
STATUS optional
DESCRIPTION
        " "
::= { baseinfo1 37 }

outlet23WarnStatPDU4 OBJECT-TYPE
SYNTAX INTEGER (0..127)
ACCESS read-only
STATUS optional
DESCRIPTION
        " "
::= { baseinfo1 38 }

outlet24WarnStatPDU4 OBJECT-TYPE
SYNTAX INTEGER (0..127)
ACCESS read-only
STATUS optional
DESCRIPTION
        " "
::= { baseinfo1 39 }

outlet25WarnStatPDU4 OBJECT-TYPE
SYNTAX INTEGER (0..127)
ACCESS read-only
STATUS optional
DESCRIPTION
        " "
::= { baseinfo1 40 }

outlet26WarnStatPDU4 OBJECT-TYPE
SYNTAX INTEGER (0..127)
ACCESS read-only
STATUS optional
DESCRIPTION
        " "
::= { baseinfo1 41 }

outlet27WarnStatPDU4 OBJECT-TYPE
SYNTAX INTEGER (0..127)
ACCESS read-only
STATUS optional
DESCRIPTION
        " "
::= { baseinfo1 42 }

outlet28WarnStatPDU4 OBJECT-TYPE
SYNTAX INTEGER (0..127)
ACCESS read-only
STATUS optional
DESCRIPTION
        " "
::= { baseinfo1 43 }

outlet29WarnStatPDU4 OBJECT-TYPE
SYNTAX INTEGER (0..127)
ACCESS read-only
STATUS optional
DESCRIPTION
        " "
::= { baseinfo1 44 }

outlet30WarnStatPDU4 OBJECT-TYPE
SYNTAX INTEGER (0..127)
ACCESS read-only
STATUS optional
DESCRIPTION
        " "
::= { baseinfo1 45 }

outlet31WarnStatPDU4 OBJECT-TYPE
SYNTAX INTEGER (0..127)
ACCESS read-only
STATUS optional
DESCRIPTION
        " "
::= { baseinfo1 46 }

outlet32WarnStatPDU4 OBJECT-TYPE
SYNTAX INTEGER (0..127)
ACCESS read-only
STATUS optional
DESCRIPTION
        " "
::= { baseinfo1 47 }

outlet33WarnStatPDU4 OBJECT-TYPE
SYNTAX INTEGER (0..127)
ACCESS read-only
STATUS optional
DESCRIPTION
        " "
::= { baseinfo1 48 }

outlet34WarnStatPDU4 OBJECT-TYPE
SYNTAX INTEGER (0..127)
ACCESS read-only
STATUS optional
DESCRIPTION
        " "
::= { baseinfo1 49 }

outlet35WarnStatPDU4 OBJECT-TYPE
SYNTAX INTEGER (0..127)
ACCESS read-only
STATUS optional
DESCRIPTION
        " "
::= { baseinfo1 50 }

outlet36WarnStatPDU4 OBJECT-TYPE
SYNTAX INTEGER (0..127)
ACCESS read-only
STATUS optional
DESCRIPTION
        " "
::= { baseinfo1 51 }

input1 OBJECT IDENTIFIER ::= { pdu4 2 }

currentL1PDU4 OBJECT-TYPE
SYNTAX INTEGER (0..65535)
ACCESS read-only
STATUS optional
DESCRIPTION
        " "
::= { input1 1 }

voltageL1PDU4 OBJECT-TYPE
SYNTAX INTEGER (0..65535)
ACCESS read-only
STATUS optional
DESCRIPTION
        " "
::= { input1 2 }

powerL1PDU4 OBJECT-TYPE
SYNTAX INTEGER (0..65535)
ACCESS read-only
STATUS optional
DESCRIPTION
        " "
::= { input1 3 }

pfL1PDU4 OBJECT-TYPE
SYNTAX INTEGER (0..65535)
ACCESS read-only
STATUS optional
DESCRIPTION
        " "
::= { input1 4 }

energyL1PDU4 OBJECT-TYPE
SYNTAX INTEGER (0..65535)
ACCESS read-only
STATUS optional
DESCRIPTION
        " "
::= { input1 5 }

currentL2PDU4 OBJECT-TYPE
SYNTAX INTEGER (0..65535)
ACCESS read-only
STATUS optional
DESCRIPTION
        " "
::= { input1 6 }

voltageL2PDU4 OBJECT-TYPE
SYNTAX INTEGER (0..65535)
ACCESS read-only
STATUS optional
DESCRIPTION
        " "
::= { input1 7 }

powerL2PDU4 OBJECT-TYPE
SYNTAX INTEGER (0..65535)
ACCESS read-only
STATUS optional
DESCRIPTION
        " "
::= { input1 8 }

pfL2PDU4 OBJECT-TYPE
SYNTAX INTEGER (0..65535)
ACCESS read-only
STATUS optional
DESCRIPTION
        " "
::= { input1 9 }

energyL2PDU4 OBJECT-TYPE
SYNTAX INTEGER (0..65535)
ACCESS read-only
STATUS optional
DESCRIPTION
        " "
::= { input1 10 }

currentL3PDU4 OBJECT-TYPE
SYNTAX INTEGER (0..65535)
ACCESS read-only
STATUS optional
DESCRIPTION
        " "
::= { input1 11 }

voltageL3PDU4 OBJECT-TYPE
SYNTAX INTEGER (0..65535)
ACCESS read-only
STATUS optional
DESCRIPTION
        " "
::= { input1 12 }

powerL3PDU4 OBJECT-TYPE
SYNTAX INTEGER (0..65535)
ACCESS read-only
STATUS optional
DESCRIPTION
        " "
::= { input1 13 }

pfL3PDU4 OBJECT-TYPE
SYNTAX INTEGER (0..65535)
ACCESS read-only
STATUS optional
DESCRIPTION
        " "
::= { input1 14 }

energyL3PDU4 OBJECT-TYPE
SYNTAX INTEGER (0..65535)
ACCESS read-only
STATUS optional
DESCRIPTION
        " "
::= { input1 15 }

outletinfo1 OBJECT IDENTIFIER ::= { pdu4 3 }

outlet1PDU4 OBJECT IDENTIFIER ::= { outletinfo1 1 }

outlet2PDU4 OBJECT IDENTIFIER ::= { outletinfo1 2 }

outlet3PDU4 OBJECT IDENTIFIER ::= { outletinfo1 3 }

outlet4PDU4 OBJECT IDENTIFIER ::= { outletinfo1 4 }

outlet5PDU4 OBJECT IDENTIFIER ::= { outletinfo1 5 }

outlet6PDU4 OBJECT IDENTIFIER ::= { outletinfo1 6 }

outlet7PDU4 OBJECT IDENTIFIER ::= { outletinfo1 7 }

outlet8PDU4 OBJECT IDENTIFIER ::= { outletinfo1 8 }

outlet9PDU4 OBJECT IDENTIFIER ::= { outletinfo1 9 }

outlet10PDU4 OBJECT IDENTIFIER ::= { outletinfo1 10 }

outlet11PDU4 OBJECT IDENTIFIER ::= { outletinfo1 11 }

outlet12PDU4 OBJECT IDENTIFIER ::= { outletinfo1 12 }

outlet13PDU4 OBJECT IDENTIFIER ::= { outletinfo1 13 }

outlet14PDU4 OBJECT IDENTIFIER ::= { outletinfo1 14 }

outlet15PDU4 OBJECT IDENTIFIER ::= { outletinfo1 15 }

outlet16PDU4 OBJECT IDENTIFIER ::= { outletinfo1 16 }

outlet17PDU4 OBJECT IDENTIFIER ::= { outletinfo1 17 }

outlet18PDU4 OBJECT IDENTIFIER ::= { outletinfo1 18 }

outlet19PDU4 OBJECT IDENTIFIER ::= { outletinfo1 19 }

outlet20PDU4 OBJECT IDENTIFIER ::= { outletinfo1 20 }

outlet21PDU4 OBJECT IDENTIFIER ::= { outletinfo1 21 }

outlet22PDU4 OBJECT IDENTIFIER ::= { outletinfo1 22 }

outlet23PDU4 OBJECT IDENTIFIER ::= { outletinfo1 23 }

outlet24PDU4 OBJECT IDENTIFIER ::= { outletinfo1 24 }

outlet25PDU4 OBJECT IDENTIFIER ::= { outletinfo1 25 }

outlet26PDU4 OBJECT IDENTIFIER ::= { outletinfo1 26 }

outlet27PDU4 OBJECT IDENTIFIER ::= { outletinfo1 27 }

outlet28PDU4 OBJECT IDENTIFIER ::= { outletinfo1 28 }

outlet29PDU4 OBJECT IDENTIFIER ::= { outletinfo1 29 }

outlet30PDU4 OBJECT IDENTIFIER ::= { outletinfo1 30 }

outlet31PDU4 OBJECT IDENTIFIER ::= { outletinfo1 31 }

outlet32PDU4 OBJECT IDENTIFIER ::= { outletinfo1 32 }

outlet33PDU4 OBJECT IDENTIFIER ::= { outletinfo1 33 }

outlet34PDU4 OBJECT IDENTIFIER ::= { outletinfo1 34 }

outlet35PDU4 OBJECT IDENTIFIER ::= { outletinfo1 35 }

outlet36PDU4 OBJECT IDENTIFIER ::= { outletinfo1 36 }

switch1PDU4 OBJECT-TYPE
SYNTAX INTEGER (0..3)
ACCESS read-write
STATUS optional
DESCRIPTION
        " "
::= { outlet1PDU4 1 }

voltage1PDU4 OBJECT-TYPE
SYNTAX INTEGER (0..65535)
ACCESS read-only
STATUS optional
DESCRIPTION
        " "
::= { outlet1PDU4 2 }

current1PDU4 OBJECT-TYPE
SYNTAX INTEGER (0..65535)
ACCESS read-only
STATUS optional
DESCRIPTION
        " "
::= { outlet1PDU4 3 }

power1PDU4 OBJECT-TYPE
SYNTAX INTEGER (0..65535)
ACCESS read-only
STATUS optional
DESCRIPTION
        " "
::= { outlet1PDU4 4 }

pf1PDU4 OBJECT-TYPE
SYNTAX INTEGER (0..65535)
ACCESS read-only
STATUS optional
DESCRIPTION
        " "
::= { outlet1PDU4 5 }

energy1PDU4 OBJECT-TYPE
SYNTAX INTEGER (0..65535)
ACCESS read-only
STATUS optional
DESCRIPTION
        " "
::= { outlet1PDU4 6 }

switch2PDU4 OBJECT-TYPE
SYNTAX INTEGER (0..3)
ACCESS read-write
STATUS optional
DESCRIPTION
        " "
::= { outlet2PDU4 1 }

voltage2PDU4 OBJECT-TYPE
SYNTAX INTEGER (0..65535)
ACCESS read-only
STATUS optional
DESCRIPTION
        " "
::= { outlet2PDU4 2 }

current2PDU4 OBJECT-TYPE
SYNTAX INTEGER (0..65535)
ACCESS read-only
STATUS optional
DESCRIPTION
        " "
::= { outlet2PDU4 3 }

power2PDU4 OBJECT-TYPE
SYNTAX INTEGER (0..65535)
ACCESS read-only
STATUS optional
DESCRIPTION
        " "
::= { outlet2PDU4 4 }

pf2PDU4 OBJECT-TYPE
SYNTAX INTEGER (0..65535)
ACCESS read-only
STATUS optional
DESCRIPTION
        " "
::= { outlet2PDU4 5 }

energy2PDU4 OBJECT-TYPE
SYNTAX INTEGER (0..65535)
ACCESS read-only
STATUS optional
DESCRIPTION
        " "
::= { outlet2PDU4 6 }

switch3PDU4 OBJECT-TYPE
SYNTAX INTEGER (0..3)
ACCESS read-write
STATUS optional
DESCRIPTION
        " "
::= { outlet3PDU4 1 }

voltage3PDU4 OBJECT-TYPE
SYNTAX INTEGER (0..65535)
ACCESS read-only
STATUS optional
DESCRIPTION
        " "
::= { outlet3PDU4 2 }

current3PDU4 OBJECT-TYPE
SYNTAX INTEGER (0..65535)
ACCESS read-only
STATUS optional
DESCRIPTION
        " "
::= { outlet3PDU4 3 }

power3PDU4 OBJECT-TYPE
SYNTAX INTEGER (0..65535)
ACCESS read-only
STATUS optional
DESCRIPTION
        " "
::= { outlet3PDU4 4 }

pf3PDU4 OBJECT-TYPE
SYNTAX INTEGER (0..65535)
ACCESS read-only
STATUS optional
DESCRIPTION
        " "
::= { outlet3PDU4 5 }

energy3PDU4 OBJECT-TYPE
SYNTAX INTEGER (0..65535)
ACCESS read-only
STATUS optional
DESCRIPTION
        " "
::= { outlet3PDU4 6 }

switch4PDU4 OBJECT-TYPE
SYNTAX INTEGER (0..3)
ACCESS read-write
STATUS optional
DESCRIPTION
        " "
::= { outlet4PDU4 1 }

voltage4PDU4 OBJECT-TYPE
SYNTAX INTEGER (0..65535)
ACCESS read-only
STATUS optional
DESCRIPTION
        " "
::= { outlet4PDU4 2 }

current4PDU4 OBJECT-TYPE
SYNTAX INTEGER (0..65535)
ACCESS read-only
STATUS optional
DESCRIPTION
        " "
::= { outlet4PDU4 3 }

power4PDU4 OBJECT-TYPE
SYNTAX INTEGER (0..65535)
ACCESS read-only
STATUS optional
DESCRIPTION
        " "
::= { outlet4PDU4 4 }

pf4PDU4 OBJECT-TYPE
SYNTAX INTEGER (0..65535)
ACCESS read-only
STATUS optional
DESCRIPTION
        " "
::= { outlet4PDU4 5 }

energy4PDU4 OBJECT-TYPE
SYNTAX INTEGER (0..65535)
ACCESS read-only
STATUS optional
DESCRIPTION
        " "
::= { outlet4PDU4 6 }

switch5PDU4 OBJECT-TYPE
SYNTAX INTEGER (0..3)
ACCESS read-write
STATUS optional
DESCRIPTION
        " "
::= { outlet5PDU4 1 }

voltage5PDU4 OBJECT-TYPE
SYNTAX INTEGER (0..65535)
ACCESS read-only
STATUS optional
DESCRIPTION
        " "
::= { outlet5PDU4 2 }

current5PDU4 OBJECT-TYPE
SYNTAX INTEGER (0..65535)
ACCESS read-only
STATUS optional
DESCRIPTION
        " "
::= { outlet5PDU4 3 }

power5PDU4 OBJECT-TYPE
SYNTAX INTEGER (0..65535)
ACCESS read-only
STATUS optional
DESCRIPTION
        " "
::= { outlet5PDU4 4 }

pf5PDU4 OBJECT-TYPE
SYNTAX INTEGER (0..65535)
ACCESS read-only
STATUS optional
DESCRIPTION
        " "
::= { outlet5PDU4 5 }

energy5PDU4 OBJECT-TYPE
SYNTAX INTEGER (0..65535)
ACCESS read-only
STATUS optional
DESCRIPTION
        " "
::= { outlet5PDU4 6 }

switch6PDU4 OBJECT-TYPE
SYNTAX INTEGER (0..3)
ACCESS read-write
STATUS optional
DESCRIPTION
        " "
::= { outlet6PDU4 1 }

voltage6PDU4 OBJECT-TYPE
SYNTAX INTEGER (0..65535)
ACCESS read-only
STATUS optional
DESCRIPTION
        " "
::= { outlet6PDU4 2 }

current6PDU4 OBJECT-TYPE
SYNTAX INTEGER (0..65535)
ACCESS read-only
STATUS optional
DESCRIPTION
        " "
::= { outlet6PDU4 3 }

power6PDU4 OBJECT-TYPE
SYNTAX INTEGER (0..65535)
ACCESS read-only
STATUS optional
DESCRIPTION
        " "
::= { outlet6PDU4 4 }

pf6PDU4 OBJECT-TYPE
SYNTAX INTEGER (0..65535)
ACCESS read-only
STATUS optional
DESCRIPTION
        " "
::= { outlet6PDU4 5 }

energy6PDU4 OBJECT-TYPE
SYNTAX INTEGER (0..65535)
ACCESS read-only
STATUS optional
DESCRIPTION
        " "
::= { outlet6PDU4 6 }

switch7PDU4 OBJECT-TYPE
SYNTAX INTEGER (0..3)
ACCESS read-write
STATUS optional
DESCRIPTION
        " "
::= { outlet7PDU4 1 }

voltage7PDU4 OBJECT-TYPE
SYNTAX INTEGER (0..65535)
ACCESS read-only
STATUS optional
DESCRIPTION
        " "
::= { outlet7PDU4 2 }

current7PDU4 OBJECT-TYPE
SYNTAX INTEGER (0..65535)
ACCESS read-only
STATUS optional
DESCRIPTION
        " "
::= { outlet7PDU4 3 }

power7PDU4 OBJECT-TYPE
SYNTAX INTEGER (0..65535)
ACCESS read-only
STATUS optional
DESCRIPTION
        " "
::= { outlet7PDU4 4 }

pf7PDU4 OBJECT-TYPE
SYNTAX INTEGER (0..65535)
ACCESS read-only
STATUS optional
DESCRIPTION
        " "
::= { outlet7PDU4 5 }

energy7PDU4 OBJECT-TYPE
SYNTAX INTEGER (0..65535)
ACCESS read-only
STATUS optional
DESCRIPTION
        " "
::= { outlet7PDU4 6 }

switch8PDU4 OBJECT-TYPE
SYNTAX INTEGER (0..3)
ACCESS read-write
STATUS optional
DESCRIPTION
        " "
::= { outlet8PDU4 1 }

voltage8PDU4 OBJECT-TYPE
SYNTAX INTEGER (0..65535)
ACCESS read-only
STATUS optional
DESCRIPTION
        " "
::= { outlet8PDU4 2 }

current8PDU4 OBJECT-TYPE
SYNTAX INTEGER (0..65535)
ACCESS read-only
STATUS optional
DESCRIPTION
        " "
::= { outlet8PDU4 3 }

power8PDU4 OBJECT-TYPE
SYNTAX INTEGER (0..65535)
ACCESS read-only
STATUS optional
DESCRIPTION
        " "
::= { outlet8PDU4 4 }

pf8PDU4 OBJECT-TYPE
SYNTAX INTEGER (0..65535)
ACCESS read-only
STATUS optional
DESCRIPTION
        " "
::= { outlet8PDU4 5 }

energy8PDU4 OBJECT-TYPE
SYNTAX INTEGER (0..65535)
ACCESS read-only
STATUS optional
DESCRIPTION
        " "
::= { outlet8PDU4 6 }

switch9PDU4 OBJECT-TYPE
SYNTAX INTEGER (0..3)
ACCESS read-write
STATUS optional
DESCRIPTION
        " "
::= { outlet9PDU4 1 }

voltage9PDU4 OBJECT-TYPE
SYNTAX INTEGER (0..65535)
ACCESS read-only
STATUS optional
DESCRIPTION
        " "
::= { outlet9PDU4 2 }

current9PDU4 OBJECT-TYPE
SYNTAX INTEGER (0..65535)
ACCESS read-only
STATUS optional
DESCRIPTION
        " "
::= { outlet9PDU4 3 }

power9PDU4 OBJECT-TYPE
SYNTAX INTEGER (0..65535)
ACCESS read-only
STATUS optional
DESCRIPTION
        " "
::= { outlet9PDU4 4 }

pf9PDU4 OBJECT-TYPE
SYNTAX INTEGER (0..65535)
ACCESS read-only
STATUS optional
DESCRIPTION
        " "
::= { outlet9PDU4 5 }

energy9PDU4 OBJECT-TYPE
SYNTAX INTEGER (0..65535)
ACCESS read-only
STATUS optional
DESCRIPTION
        " "
::= { outlet9PDU4 6 }

switch10PDU4 OBJECT-TYPE
SYNTAX INTEGER (0..3)
ACCESS read-write
STATUS optional
DESCRIPTION
        " "
::= { outlet10PDU4 1 }

voltage10PDU4 OBJECT-TYPE
SYNTAX INTEGER (0..65535)
ACCESS read-only
STATUS optional
DESCRIPTION
        " "
::= { outlet10PDU4 2 }

current10PDU4 OBJECT-TYPE
SYNTAX INTEGER (0..65535)
ACCESS read-only
STATUS optional
DESCRIPTION
        " "
::= { outlet10PDU4 3 }

power10PDU4 OBJECT-TYPE
SYNTAX INTEGER (0..65535)
ACCESS read-only
STATUS optional
DESCRIPTION
        " "
::= { outlet10PDU4 4 }

pf10PDU4 OBJECT-TYPE
SYNTAX INTEGER (0..65535)
ACCESS read-only
STATUS optional
DESCRIPTION
        " "
::= { outlet10PDU4 5 }

energy10PDU4 OBJECT-TYPE
SYNTAX INTEGER (0..65535)
ACCESS read-only
STATUS optional
DESCRIPTION
        " "
::= { outlet10PDU4 6 }

switch11PDU4 OBJECT-TYPE
SYNTAX INTEGER (0..3)
ACCESS read-write
STATUS optional
DESCRIPTION
        " "
::= { outlet11PDU4 1 }

voltage11PDU4 OBJECT-TYPE
SYNTAX INTEGER (0..65535)
ACCESS read-only
STATUS optional
DESCRIPTION
        " "
::= { outlet11PDU4 2 }

current11PDU4 OBJECT-TYPE
SYNTAX INTEGER (0..65535)
ACCESS read-only
STATUS optional
DESCRIPTION
        " "
::= { outlet11PDU4 3 }

power11PDU4 OBJECT-TYPE
SYNTAX INTEGER (0..65535)
ACCESS read-only
STATUS optional
DESCRIPTION
        " "
::= { outlet11PDU4 4 }

pf11PDU4 OBJECT-TYPE
SYNTAX INTEGER (0..65535)
ACCESS read-only
STATUS optional
DESCRIPTION
        " "
::= { outlet11PDU4 5 }

energy11PDU4 OBJECT-TYPE
SYNTAX INTEGER (0..65535)
ACCESS read-only
STATUS optional
DESCRIPTION
        " "
::= { outlet11PDU4 6 }

switch12PDU4 OBJECT-TYPE
SYNTAX INTEGER (0..3)
ACCESS read-write
STATUS optional
DESCRIPTION
        " "
::= { outlet12PDU4 1 }

voltage12PDU4 OBJECT-TYPE
SYNTAX INTEGER (0..65535)
ACCESS read-only
STATUS optional
DESCRIPTION
        " "
::= { outlet12PDU4 2 }

current12PDU4 OBJECT-TYPE
SYNTAX INTEGER (0..65535)
ACCESS read-only
STATUS optional
DESCRIPTION
        " "
::= { outlet12PDU4 3 }

power12PDU4 OBJECT-TYPE
SYNTAX INTEGER (0..65535)
ACCESS read-only
STATUS optional
DESCRIPTION
        " "
::= { outlet12PDU4 4 }

pf12PDU4 OBJECT-TYPE
SYNTAX INTEGER (0..65535)
ACCESS read-only
STATUS optional
DESCRIPTION
        " "
::= { outlet12PDU4 5 }

energy12PDU4 OBJECT-TYPE
SYNTAX INTEGER (0..65535)
ACCESS read-only
STATUS optional
DESCRIPTION
        " "
::= { outlet12PDU4 6 }

switch13PDU4 OBJECT-TYPE
SYNTAX INTEGER (0..3)
ACCESS read-write
STATUS optional
DESCRIPTION
        " "
::= { outlet13PDU4 1 }

voltage13PDU4 OBJECT-TYPE
SYNTAX INTEGER (0..65535)
ACCESS read-only
STATUS optional
DESCRIPTION
        " "
::= { outlet13PDU4 2 }

current13PDU4 OBJECT-TYPE
SYNTAX INTEGER (0..65535)
ACCESS read-only
STATUS optional
DESCRIPTION
        " "
::= { outlet13PDU4 3 }

power13PDU4 OBJECT-TYPE
SYNTAX INTEGER (0..65535)
ACCESS read-only
STATUS optional
DESCRIPTION
        " "
::= { outlet13PDU4 4 }

pf13PDU4 OBJECT-TYPE
SYNTAX INTEGER (0..65535)
ACCESS read-only
STATUS optional
DESCRIPTION
        " "
::= { outlet13PDU4 5 }

energy13PDU4 OBJECT-TYPE
SYNTAX INTEGER (0..65535)
ACCESS read-only
STATUS optional
DESCRIPTION
        " "
::= { outlet13PDU4 6 }

switch14PDU4 OBJECT-TYPE
SYNTAX INTEGER (0..3)
ACCESS read-write
STATUS optional
DESCRIPTION
        " "
::= { outlet14PDU4 1 }

voltage14PDU4 OBJECT-TYPE
SYNTAX INTEGER (0..65535)
ACCESS read-only
STATUS optional
DESCRIPTION
        " "
::= { outlet14PDU4 2 }

current14PDU4 OBJECT-TYPE
SYNTAX INTEGER (0..65535)
ACCESS read-only
STATUS optional
DESCRIPTION
        " "
::= { outlet14PDU4 3 }

power14PDU4 OBJECT-TYPE
SYNTAX INTEGER (0..65535)
ACCESS read-only
STATUS optional
DESCRIPTION
        " "
::= { outlet14PDU4 4 }

pf14PDU4 OBJECT-TYPE
SYNTAX INTEGER (0..65535)
ACCESS read-only
STATUS optional
DESCRIPTION
        " "
::= { outlet14PDU4 5 }

energy14PDU4 OBJECT-TYPE
SYNTAX INTEGER (0..65535)
ACCESS read-only
STATUS optional
DESCRIPTION
        " "
::= { outlet14PDU4 6 }

switch15PDU4 OBJECT-TYPE
SYNTAX INTEGER (0..3)
ACCESS read-write
STATUS optional
DESCRIPTION
        " "
::= { outlet15PDU4 1 }

voltage15PDU4 OBJECT-TYPE
SYNTAX INTEGER (0..65535)
ACCESS read-only
STATUS optional
DESCRIPTION
        " "
::= { outlet15PDU4 2 }

current15PDU4 OBJECT-TYPE
SYNTAX INTEGER (0..65535)
ACCESS read-only
STATUS optional
DESCRIPTION
        " "
::= { outlet15PDU4 3 }

power15PDU4 OBJECT-TYPE
SYNTAX INTEGER (0..65535)
ACCESS read-only
STATUS optional
DESCRIPTION
        " "
::= { outlet15PDU4 4 }

pf15PDU4 OBJECT-TYPE
SYNTAX INTEGER (0..65535)
ACCESS read-only
STATUS optional
DESCRIPTION
        " "
::= { outlet15PDU4 5 }

energy15PDU4 OBJECT-TYPE
SYNTAX INTEGER (0..65535)
ACCESS read-only
STATUS optional
DESCRIPTION
        " "
::= { outlet15PDU4 6 }

switch16PDU4 OBJECT-TYPE
SYNTAX INTEGER (0..3)
ACCESS read-write
STATUS optional
DESCRIPTION
        " "
::= { outlet16PDU4 1 }

voltage16PDU4 OBJECT-TYPE
SYNTAX INTEGER (0..65535)
ACCESS read-only
STATUS optional
DESCRIPTION
        " "
::= { outlet16PDU4 2 }

current16PDU4 OBJECT-TYPE
SYNTAX INTEGER (0..65535)
ACCESS read-only
STATUS optional
DESCRIPTION
        " "
::= { outlet16PDU4 3 }

power16PDU4 OBJECT-TYPE
SYNTAX INTEGER (0..65535)
ACCESS read-only
STATUS optional
DESCRIPTION
        " "
::= { outlet16PDU4 4 }

pf16PDU4 OBJECT-TYPE
SYNTAX INTEGER (0..65535)
ACCESS read-only
STATUS optional
DESCRIPTION
        " "
::= { outlet16PDU4 5 }

energy16PDU4 OBJECT-TYPE
SYNTAX INTEGER (0..65535)
ACCESS read-only
STATUS optional
DESCRIPTION
        " "
::= { outlet16PDU4 6 }

switch17PDU4 OBJECT-TYPE
SYNTAX INTEGER (0..3)
ACCESS read-write
STATUS optional
DESCRIPTION
        " "
::= { outlet17PDU4 1 }

voltage17PDU4 OBJECT-TYPE
SYNTAX INTEGER (0..65535)
ACCESS read-only
STATUS optional
DESCRIPTION
        " "
::= { outlet17PDU4 2 }

current17PDU4 OBJECT-TYPE
SYNTAX INTEGER (0..65535)
ACCESS read-only
STATUS optional
DESCRIPTION
        " "
::= { outlet17PDU4 3 }

power17PDU4 OBJECT-TYPE
SYNTAX INTEGER (0..65535)
ACCESS read-only
STATUS optional
DESCRIPTION
        " "
::= { outlet17PDU4 4 }

pf17PDU4 OBJECT-TYPE
SYNTAX INTEGER (0..65535)
ACCESS read-only
STATUS optional
DESCRIPTION
        " "
::= { outlet17PDU4 5 }

energy17PDU4 OBJECT-TYPE
SYNTAX INTEGER (0..65535)
ACCESS read-only
STATUS optional
DESCRIPTION
        " "
::= { outlet17PDU4 6 }

switch18PDU4 OBJECT-TYPE
SYNTAX INTEGER (0..3)
ACCESS read-write
STATUS optional
DESCRIPTION
        " "
::= { outlet18PDU4 1 }

voltage18PDU4 OBJECT-TYPE
SYNTAX INTEGER (0..65535)
ACCESS read-only
STATUS optional
DESCRIPTION
        " "
::= { outlet18PDU4 2 }

current18PDU4 OBJECT-TYPE
SYNTAX INTEGER (0..65535)
ACCESS read-only
STATUS optional
DESCRIPTION
        " "
::= { outlet18PDU4 3 }

power18PDU4 OBJECT-TYPE
SYNTAX INTEGER (0..65535)
ACCESS read-only
STATUS optional
DESCRIPTION
        " "
::= { outlet18PDU4 4 }

pf18PDU4 OBJECT-TYPE
SYNTAX INTEGER (0..65535)
ACCESS read-only
STATUS optional
DESCRIPTION
        " "
::= { outlet18PDU4 5 }

energy18PDU4 OBJECT-TYPE
SYNTAX INTEGER (0..65535)
ACCESS read-only
STATUS optional
DESCRIPTION
        " "
::= { outlet18PDU4 6 }

switch19PDU4 OBJECT-TYPE
SYNTAX INTEGER (0..3)
ACCESS read-write
STATUS optional
DESCRIPTION
        " "
::= { outlet19PDU4 1 }

voltage19PDU4 OBJECT-TYPE
SYNTAX INTEGER (0..65535)
ACCESS read-only
STATUS optional
DESCRIPTION
        " "
::= { outlet19PDU4 2 }

current19PDU4 OBJECT-TYPE
SYNTAX INTEGER (0..65535)
ACCESS read-only
STATUS optional
DESCRIPTION
        " "
::= { outlet19PDU4 3 }

power19PDU4 OBJECT-TYPE
SYNTAX INTEGER (0..65535)
ACCESS read-only
STATUS optional
DESCRIPTION
        " "
::= { outlet19PDU4 4 }

pf19PDU4 OBJECT-TYPE
SYNTAX INTEGER (0..65535)
ACCESS read-only
STATUS optional
DESCRIPTION
        " "
::= { outlet19PDU4 5 }

energy19PDU4 OBJECT-TYPE
SYNTAX INTEGER (0..65535)
ACCESS read-only
STATUS optional
DESCRIPTION
        " "
::= { outlet19PDU4 6 }

switch20PDU4 OBJECT-TYPE
SYNTAX INTEGER (0..3)
ACCESS read-write
STATUS optional
DESCRIPTION
        " "
::= { outlet20PDU4 1 }

voltage20PDU4 OBJECT-TYPE
SYNTAX INTEGER (0..65535)
ACCESS read-only
STATUS optional
DESCRIPTION
        " "
::= { outlet20PDU4 2 }

current20PDU4 OBJECT-TYPE
SYNTAX INTEGER (0..65535)
ACCESS read-only
STATUS optional
DESCRIPTION
        " "
::= { outlet20PDU4 3 }

power20PDU4 OBJECT-TYPE
SYNTAX INTEGER (0..65535)
ACCESS read-only
STATUS optional
DESCRIPTION
        " "
::= { outlet20PDU4 4 }

pf20PDU4 OBJECT-TYPE
SYNTAX INTEGER (0..65535)
ACCESS read-only
STATUS optional
DESCRIPTION
        " "
::= { outlet20PDU4 5 }

energy20PDU4 OBJECT-TYPE
SYNTAX INTEGER (0..65535)
ACCESS read-only
STATUS optional
DESCRIPTION
        " "
::= { outlet20PDU4 6 }

switch21PDU4 OBJECT-TYPE
SYNTAX INTEGER (0..3)
ACCESS read-write
STATUS optional
DESCRIPTION
        " "
::= { outlet21PDU4 1 }

voltage21PDU4 OBJECT-TYPE
SYNTAX INTEGER (0..65535)
ACCESS read-only
STATUS optional
DESCRIPTION
        " "
::= { outlet21PDU4 2 }

current21PDU4 OBJECT-TYPE
SYNTAX INTEGER (0..65535)
ACCESS read-only
STATUS optional
DESCRIPTION
        " "
::= { outlet21PDU4 3 }

power21PDU4 OBJECT-TYPE
SYNTAX INTEGER (0..65535)
ACCESS read-only
STATUS optional
DESCRIPTION
        " "
::= { outlet21PDU4 4 }

pf21PDU4 OBJECT-TYPE
SYNTAX INTEGER (0..65535)
ACCESS read-only
STATUS optional
DESCRIPTION
        " "
::= { outlet21PDU4 5 }

energy21PDU4 OBJECT-TYPE
SYNTAX INTEGER (0..65535)
ACCESS read-only
STATUS optional
DESCRIPTION
        " "
::= { outlet21PDU4 6 }

switch22PDU4 OBJECT-TYPE
SYNTAX INTEGER (0..3)
ACCESS read-write
STATUS optional
DESCRIPTION
        " "
::= { outlet22PDU4 1 }

voltage22PDU4 OBJECT-TYPE
SYNTAX INTEGER (0..65535)
ACCESS read-only
STATUS optional
DESCRIPTION
        " "
::= { outlet22PDU4 2 }

current22PDU4 OBJECT-TYPE
SYNTAX INTEGER (0..65535)
ACCESS read-only
STATUS optional
DESCRIPTION
        " "
::= { outlet22PDU4 3 }

power22PDU4 OBJECT-TYPE
SYNTAX INTEGER (0..65535)
ACCESS read-only
STATUS optional
DESCRIPTION
        " "
::= { outlet22PDU4 4 }

pf22PDU4 OBJECT-TYPE
SYNTAX INTEGER (0..65535)
ACCESS read-only
STATUS optional
DESCRIPTION
        " "
::= { outlet22PDU4 5 }

energy22PDU4 OBJECT-TYPE
SYNTAX INTEGER (0..65535)
ACCESS read-only
STATUS optional
DESCRIPTION
        " "
::= { outlet22PDU4 6 }

switch23PDU4 OBJECT-TYPE
SYNTAX INTEGER (0..3)
ACCESS read-write
STATUS optional
DESCRIPTION
        " "
::= { outlet23PDU4 1 }

voltage23PDU4 OBJECT-TYPE
SYNTAX INTEGER (0..65535)
ACCESS read-only
STATUS optional
DESCRIPTION
        " "
::= { outlet23PDU4 2 }

current23PDU4 OBJECT-TYPE
SYNTAX INTEGER (0..65535)
ACCESS read-only
STATUS optional
DESCRIPTION
        " "
::= { outlet23PDU4 3 }

power23PDU4 OBJECT-TYPE
SYNTAX INTEGER (0..65535)
ACCESS read-only
STATUS optional
DESCRIPTION
        " "
::= { outlet23PDU4 4 }

pf23PDU4 OBJECT-TYPE
SYNTAX INTEGER (0..65535)
ACCESS read-only
STATUS optional
DESCRIPTION
        " "
::= { outlet23PDU4 5 }

energy23PDU4 OBJECT-TYPE
SYNTAX INTEGER (0..65535)
ACCESS read-only
STATUS optional
DESCRIPTION
        " "
::= { outlet23PDU4 6 }

switch24PDU4 OBJECT-TYPE
SYNTAX INTEGER (0..3)
ACCESS read-write
STATUS optional
DESCRIPTION
        " "
::= { outlet24PDU4 1 }

voltage24PDU4 OBJECT-TYPE
SYNTAX INTEGER (0..65535)
ACCESS read-only
STATUS optional
DESCRIPTION
        " "
::= { outlet24PDU4 2 }

current24PDU4 OBJECT-TYPE
SYNTAX INTEGER (0..65535)
ACCESS read-only
STATUS optional
DESCRIPTION
        " "
::= { outlet24PDU4 3 }

power24PDU4 OBJECT-TYPE
SYNTAX INTEGER (0..65535)
ACCESS read-only
STATUS optional
DESCRIPTION
        " "
::= { outlet24PDU4 4 }

pf24PDU4 OBJECT-TYPE
SYNTAX INTEGER (0..65535)
ACCESS read-only
STATUS optional
DESCRIPTION
        " "
::= { outlet24PDU4 5 }

energy24PDU4 OBJECT-TYPE
SYNTAX INTEGER (0..65535)
ACCESS read-only
STATUS optional
DESCRIPTION
        " "
::= { outlet24PDU4 6 }

switch25PDU4 OBJECT-TYPE
SYNTAX INTEGER (0..3)
ACCESS read-write
STATUS optional
DESCRIPTION
        " "
::= { outlet25PDU4 1 }

voltage25PDU4 OBJECT-TYPE
SYNTAX INTEGER (0..65535)
ACCESS read-only
STATUS optional
DESCRIPTION
        " "
::= { outlet25PDU4 2 }

current25PDU4 OBJECT-TYPE
SYNTAX INTEGER (0..65535)
ACCESS read-only
STATUS optional
DESCRIPTION
        " "
::= { outlet25PDU4 3 }

power25PDU4 OBJECT-TYPE
SYNTAX INTEGER (0..65535)
ACCESS read-only
STATUS optional
DESCRIPTION
        " "
::= { outlet25PDU4 4 }

pf25PDU4 OBJECT-TYPE
SYNTAX INTEGER (0..65535)
ACCESS read-only
STATUS optional
DESCRIPTION
        " "
::= { outlet25PDU4 5 }

energy25PDU4 OBJECT-TYPE
SYNTAX INTEGER (0..65535)
ACCESS read-only
STATUS optional
DESCRIPTION
        " "
::= { outlet25PDU4 6 }

switch26PDU4 OBJECT-TYPE
SYNTAX INTEGER (0..3)
ACCESS read-write
STATUS optional
DESCRIPTION
        " "
::= { outlet26PDU4 1 }

voltage26PDU4 OBJECT-TYPE
SYNTAX INTEGER (0..65535)
ACCESS read-only
STATUS optional
DESCRIPTION
        " "
::= { outlet26PDU4 2 }

current26PDU4 OBJECT-TYPE
SYNTAX INTEGER (0..65535)
ACCESS read-only
STATUS optional
DESCRIPTION
        " "
::= { outlet26PDU4 3 }

power26PDU4 OBJECT-TYPE
SYNTAX INTEGER (0..65535)
ACCESS read-only
STATUS optional
DESCRIPTION
        " "
::= { outlet26PDU4 4 }

pf26PDU4 OBJECT-TYPE
SYNTAX INTEGER (0..65535)
ACCESS read-only
STATUS optional
DESCRIPTION
        " "
::= { outlet26PDU4 5 }

energy26PDU4 OBJECT-TYPE
SYNTAX INTEGER (0..65535)
ACCESS read-only
STATUS optional
DESCRIPTION
        " "
::= { outlet26PDU4 6 }

switch27PDU4 OBJECT-TYPE
SYNTAX INTEGER (0..3)
ACCESS read-write
STATUS optional
DESCRIPTION
        " "
::= { outlet27PDU4 1 }

voltage27PDU4 OBJECT-TYPE
SYNTAX INTEGER (0..65535)
ACCESS read-only
STATUS optional
DESCRIPTION
        " "
::= { outlet27PDU4 2 }

current27PDU4 OBJECT-TYPE
SYNTAX INTEGER (0..65535)
ACCESS read-only
STATUS optional
DESCRIPTION
        " "
::= { outlet27PDU4 3 }

power27PDU4 OBJECT-TYPE
SYNTAX INTEGER (0..65535)
ACCESS read-only
STATUS optional
DESCRIPTION
        " "
::= { outlet27PDU4 4 }

pf27PDU4 OBJECT-TYPE
SYNTAX INTEGER (0..65535)
ACCESS read-only
STATUS optional
DESCRIPTION
        " "
::= { outlet27PDU4 5 }

energy27PDU4 OBJECT-TYPE
SYNTAX INTEGER (0..65535)
ACCESS read-only
STATUS optional
DESCRIPTION
        " "
::= { outlet27PDU4 6 }

switch28PDU4 OBJECT-TYPE
SYNTAX INTEGER (0..3)
ACCESS read-write
STATUS optional
DESCRIPTION
        " "
::= { outlet28PDU4 1 }

voltage28PDU4 OBJECT-TYPE
SYNTAX INTEGER (0..65535)
ACCESS read-only
STATUS optional
DESCRIPTION
        " "
::= { outlet28PDU4 2 }

current28PDU4 OBJECT-TYPE
SYNTAX INTEGER (0..65535)
ACCESS read-only
STATUS optional
DESCRIPTION
        " "
::= { outlet28PDU4 3 }

power28PDU4 OBJECT-TYPE
SYNTAX INTEGER (0..65535)
ACCESS read-only
STATUS optional
DESCRIPTION
        " "
::= { outlet28PDU4 4 }

pf28PDU4 OBJECT-TYPE
SYNTAX INTEGER (0..65535)
ACCESS read-only
STATUS optional
DESCRIPTION
        " "
::= { outlet28PDU4 5 }

energy28PDU4 OBJECT-TYPE
SYNTAX INTEGER (0..65535)
ACCESS read-only
STATUS optional
DESCRIPTION
        " "
::= { outlet28PDU4 6 }

switch29PDU4 OBJECT-TYPE
SYNTAX INTEGER (0..3)
ACCESS read-write
STATUS optional
DESCRIPTION
        " "
::= { outlet29PDU4 1 }

voltage29PDU4 OBJECT-TYPE
SYNTAX INTEGER (0..65535)
ACCESS read-only
STATUS optional
DESCRIPTION
        " "
::= { outlet29PDU4 2 }

current29PDU4 OBJECT-TYPE
SYNTAX INTEGER (0..65535)
ACCESS read-only
STATUS optional
DESCRIPTION
        " "
::= { outlet29PDU4 3 }

power29PDU4 OBJECT-TYPE
SYNTAX INTEGER (0..65535)
ACCESS read-only
STATUS optional
DESCRIPTION
        " "
::= { outlet29PDU4 4 }

pf29PDU4 OBJECT-TYPE
SYNTAX INTEGER (0..65535)
ACCESS read-only
STATUS optional
DESCRIPTION
        " "
::= { outlet29PDU4 5 }

energy29PDU4 OBJECT-TYPE
SYNTAX INTEGER (0..65535)
ACCESS read-only
STATUS optional
DESCRIPTION
        " "
::= { outlet29PDU4 6 }

switch30PDU4 OBJECT-TYPE
SYNTAX INTEGER (0..3)
ACCESS read-write
STATUS optional
DESCRIPTION
        " "
::= { outlet30PDU4 1 }

voltage30PDU4 OBJECT-TYPE
SYNTAX INTEGER (0..65535)
ACCESS read-only
STATUS optional
DESCRIPTION
        " "
::= { outlet30PDU4 2 }

current30PDU4 OBJECT-TYPE
SYNTAX INTEGER (0..65535)
ACCESS read-only
STATUS optional
DESCRIPTION
        " "
::= { outlet30PDU4 3 }

power30PDU4 OBJECT-TYPE
SYNTAX INTEGER (0..65535)
ACCESS read-only
STATUS optional
DESCRIPTION
        " "
::= { outlet30PDU4 4 }

pf30PDU4 OBJECT-TYPE
SYNTAX INTEGER (0..65535)
ACCESS read-only
STATUS optional
DESCRIPTION
        " "
::= { outlet30PDU4 5 }

energy30PDU4 OBJECT-TYPE
SYNTAX INTEGER (0..65535)
ACCESS read-only
STATUS optional
DESCRIPTION
        " "
::= { outlet30PDU4 6 }

switch31PDU4 OBJECT-TYPE
SYNTAX INTEGER (0..3)
ACCESS read-write
STATUS optional
DESCRIPTION
        " "
::= { outlet31PDU4 1 }

voltage31PDU4 OBJECT-TYPE
SYNTAX INTEGER (0..65535)
ACCESS read-only
STATUS optional
DESCRIPTION
        " "
::= { outlet31PDU4 2 }

current31PDU4 OBJECT-TYPE
SYNTAX INTEGER (0..65535)
ACCESS read-only
STATUS optional
DESCRIPTION
        " "
::= { outlet31PDU4 3 }

power31PDU4 OBJECT-TYPE
SYNTAX INTEGER (0..65535)
ACCESS read-only
STATUS optional
DESCRIPTION
        " "
::= { outlet31PDU4 4 }

pf31PDU4 OBJECT-TYPE
SYNTAX INTEGER (0..65535)
ACCESS read-only
STATUS optional
DESCRIPTION
        " "
::= { outlet31PDU4 5 }

energy31PDU4 OBJECT-TYPE
SYNTAX INTEGER (0..65535)
ACCESS read-only
STATUS optional
DESCRIPTION
        " "
::= { outlet31PDU4 6 }

switch32PDU4 OBJECT-TYPE
SYNTAX INTEGER (0..3)
ACCESS read-write
STATUS optional
DESCRIPTION
        " "
::= { outlet32PDU4 1 }

voltage32PDU4 OBJECT-TYPE
SYNTAX INTEGER (0..65535)
ACCESS read-only
STATUS optional
DESCRIPTION
        " "
::= { outlet32PDU4 2 }

current32PDU4 OBJECT-TYPE
SYNTAX INTEGER (0..65535)
ACCESS read-only
STATUS optional
DESCRIPTION
        " "
::= { outlet32PDU4 3 }

power32PDU4 OBJECT-TYPE
SYNTAX INTEGER (0..65535)
ACCESS read-only
STATUS optional
DESCRIPTION
        " "
::= { outlet32PDU4 4 }

pf32PDU4 OBJECT-TYPE
SYNTAX INTEGER (0..65535)
ACCESS read-only
STATUS optional
DESCRIPTION
        " "
::= { outlet32PDU4 5 }

energy32PDU4 OBJECT-TYPE
SYNTAX INTEGER (0..65535)
ACCESS read-only
STATUS optional
DESCRIPTION
        " "
::= { outlet32PDU4 6 }

switch33PDU4 OBJECT-TYPE
SYNTAX INTEGER (0..3)
ACCESS read-write
STATUS optional
DESCRIPTION
        " "
::= { outlet33PDU4 1 }

voltage33PDU4 OBJECT-TYPE
SYNTAX INTEGER (0..65535)
ACCESS read-only
STATUS optional
DESCRIPTION
        " "
::= { outlet33PDU4 2 }

current33PDU4 OBJECT-TYPE
SYNTAX INTEGER (0..65535)
ACCESS read-only
STATUS optional
DESCRIPTION
        " "
::= { outlet33PDU4 3 }

power33PDU4 OBJECT-TYPE
SYNTAX INTEGER (0..65535)
ACCESS read-only
STATUS optional
DESCRIPTION
        " "
::= { outlet33PDU4 4 }

pf33PDU4 OBJECT-TYPE
SYNTAX INTEGER (0..65535)
ACCESS read-only
STATUS optional
DESCRIPTION
        " "
::= { outlet33PDU4 5 }

energy33PDU4 OBJECT-TYPE
SYNTAX INTEGER (0..65535)
ACCESS read-only
STATUS optional
DESCRIPTION
        " "
::= { outlet33PDU4 6 }

switch34PDU4 OBJECT-TYPE
SYNTAX INTEGER (0..3)
ACCESS read-write
STATUS optional
DESCRIPTION
        " "
::= { outlet34PDU4 1 }

voltage34PDU4 OBJECT-TYPE
SYNTAX INTEGER (0..65535)
ACCESS read-only
STATUS optional
DESCRIPTION
        " "
::= { outlet34PDU4 2 }

current34PDU4 OBJECT-TYPE
SYNTAX INTEGER (0..65535)
ACCESS read-only
STATUS optional
DESCRIPTION
        " "
::= { outlet34PDU4 3 }

power34PDU4 OBJECT-TYPE
SYNTAX INTEGER (0..65535)
ACCESS read-only
STATUS optional
DESCRIPTION
        " "
::= { outlet34PDU4 4 }

pf34PDU4 OBJECT-TYPE
SYNTAX INTEGER (0..65535)
ACCESS read-only
STATUS optional
DESCRIPTION
        " "
::= { outlet34PDU4 5 }

energy34PDU4 OBJECT-TYPE
SYNTAX INTEGER (0..65535)
ACCESS read-only
STATUS optional
DESCRIPTION
        " "
::= { outlet34PDU4 6 }

switch35PDU4 OBJECT-TYPE
SYNTAX INTEGER (0..3)
ACCESS read-write
STATUS optional
DESCRIPTION
        " "
::= { outlet35PDU4 1 }

voltage35PDU4 OBJECT-TYPE
SYNTAX INTEGER (0..65535)
ACCESS read-only
STATUS optional
DESCRIPTION
        " "
::= { outlet35PDU4 2 }

current35PDU4 OBJECT-TYPE
SYNTAX INTEGER (0..65535)
ACCESS read-only
STATUS optional
DESCRIPTION
        " "
::= { outlet35PDU4 3 }

power35PDU4 OBJECT-TYPE
SYNTAX INTEGER (0..65535)
ACCESS read-only
STATUS optional
DESCRIPTION
        " "
::= { outlet35PDU4 4 }

pf35PDU4 OBJECT-TYPE
SYNTAX INTEGER (0..65535)
ACCESS read-only
STATUS optional
DESCRIPTION
        " "
::= { outlet35PDU4 5 }

energy35PDU4 OBJECT-TYPE
SYNTAX INTEGER (0..65535)
ACCESS read-only
STATUS optional
DESCRIPTION
        " "
::= { outlet35PDU4 6 }

switch36PDU4 OBJECT-TYPE
SYNTAX INTEGER (0..3)
ACCESS read-write
STATUS optional
DESCRIPTION
        " "
::= { outlet36PDU4 1 }

voltage36PDU4 OBJECT-TYPE
SYNTAX INTEGER (0..65535)
ACCESS read-only
STATUS optional
DESCRIPTION
        " "
::= { outlet36PDU4 2 }

current36PDU4 OBJECT-TYPE
SYNTAX INTEGER (0..65535)
ACCESS read-only
STATUS optional
DESCRIPTION
        " "
::= { outlet36PDU4 3 }

power36PDU4 OBJECT-TYPE
SYNTAX INTEGER (0..65535)
ACCESS read-only
STATUS optional
DESCRIPTION
        " "
::= { outlet36PDU4 4 }

pf36PDU4 OBJECT-TYPE
SYNTAX INTEGER (0..65535)
ACCESS read-only
STATUS optional
DESCRIPTION
        " "
::= { outlet36PDU4 5 }

energy36PDU4 OBJECT-TYPE
SYNTAX INTEGER (0..65535)
ACCESS read-only
STATUS optional
DESCRIPTION
        " "
::= { outlet36PDU4 6 }

sensor1 OBJECT IDENTIFIER ::= { pdu4 4 }

temperature1PDU4 OBJECT-TYPE
SYNTAX INTEGER (0..65535)
ACCESS read-only
STATUS optional
DESCRIPTION
        " "
::= { sensor1 1 }

humidity1PDU4 OBJECT-TYPE
SYNTAX INTEGER (0..65535)
ACCESS read-only
STATUS optional
DESCRIPTION
        " "
::= { sensor1 2 }

temperature2PDU4 OBJECT-TYPE
SYNTAX INTEGER (0..65535)
ACCESS read-only
STATUS optional
DESCRIPTION
        " "
::= { sensor1 3 }

humidity2PDU4 OBJECT-TYPE
SYNTAX INTEGER (0..65535)
ACCESS read-only
STATUS optional
DESCRIPTION
        " "
::= { sensor1 4 }

inputStatus1PDU4 OBJECT-TYPE
SYNTAX INTEGER (0..1)
ACCESS read-only
STATUS optional
DESCRIPTION
        " "
::= { sensor1 5 }

inputStatus2PDU4 OBJECT-TYPE
SYNTAX INTEGER (0..1)
ACCESS read-only
STATUS optional
DESCRIPTION
        " "
::= { sensor1 6 }

inputStatus3PDU4 OBJECT-TYPE
SYNTAX INTEGER (0..1)
ACCESS read-only
STATUS optional
DESCRIPTION
        " "
::= { sensor1 7 }

inputStatus4PDU4 OBJECT-TYPE
SYNTAX INTEGER (0..1)
ACCESS read-only
STATUS optional
DESCRIPTION
        " "
::= { sensor1 8 }

doStatus1PDU4 OBJECT-TYPE
SYNTAX INTEGER (0..1)
ACCESS read-only
STATUS optional
DESCRIPTION
        " "
::= { sensor1 9 }

doStatus2PDU4 OBJECT-TYPE
SYNTAX INTEGER (0..1)
ACCESS read-only
STATUS optional
DESCRIPTION
        " "
::= { sensor1 10 }

baseinfo1 OBJECT IDENTIFIER ::= { pdu5 1 }

cascadeAlarmPDU5 OBJECT-TYPE
SYNTAX INTEGER (0..3)
ACCESS read-only
STATUS optional
DESCRIPTION
        " "
::= { baseinfo1 1 }

deviceNamePDU5 OBJECT-TYPE
SYNTAX DisplayString (SIZE (32))
ACCESS read-write
STATUS optional
DESCRIPTION
        " "
::= { baseinfo1 2 }

outletNumberPDU5 OBJECT-TYPE
SYNTAX INTEGER (0..36)
ACCESS read-only
STATUS optional
DESCRIPTION
        " "
::= { baseinfo1 3 }

temphum1WarnStatPDU5 OBJECT-TYPE
SYNTAX INTEGER (0..127)
ACCESS read-only
STATUS optional
DESCRIPTION
        " "
::= { baseinfo1 4 }

temphum2WarnStatPDU5 OBJECT-TYPE
SYNTAX INTEGER (0..127)
ACCESS read-only
STATUS optional
DESCRIPTION
        " "
::= { baseinfo1 5 }

input1WarnStatPDU5 OBJECT-TYPE
SYNTAX INTEGER (0..1)
ACCESS read-only
STATUS optional
DESCRIPTION
        " "
::= { baseinfo1 6 }

input2WarnStatPDU5 OBJECT-TYPE
SYNTAX INTEGER (0..1)
ACCESS read-only
STATUS optional
DESCRIPTION
        " "
::= { baseinfo1 7 }

input3WarnStatPDU5 OBJECT-TYPE
SYNTAX INTEGER (0..1)
ACCESS read-only
STATUS optional
DESCRIPTION
        " "
::= { baseinfo1 8 }

input4WarnStatPDU5 OBJECT-TYPE
SYNTAX INTEGER (0..1)
ACCESS read-only
STATUS optional
DESCRIPTION
        " "
::= { baseinfo1 9 }

currentL1WarnStatPDU5 OBJECT-TYPE
SYNTAX INTEGER (0..127)
ACCESS read-only
STATUS optional
DESCRIPTION
        " "
::= { baseinfo1 10 }

currentL2WarnStatPDU5 OBJECT-TYPE
SYNTAX INTEGER (0..127)
ACCESS read-only
STATUS optional
DESCRIPTION
        " "
::= { baseinfo1 11 }

currentL3WarnStatPDU5 OBJECT-TYPE
SYNTAX INTEGER (0..127)
ACCESS read-only
STATUS optional
DESCRIPTION
        " "
::= { baseinfo1 12 }

voltageL1WarnStatPDU5 OBJECT-TYPE
SYNTAX INTEGER (0..127)
ACCESS read-only
STATUS optional
DESCRIPTION
        " "
::= { baseinfo1 13 }

voltageL2WarnStatPDU5 OBJECT-TYPE
SYNTAX INTEGER (0..127)
ACCESS read-only
STATUS optional
DESCRIPTION
        " "
::= { baseinfo1 14 }

voltageL3WarnStatPDU5 OBJECT-TYPE
SYNTAX INTEGER (0..127)
ACCESS read-only
STATUS optional
DESCRIPTION
        " "
::= { baseinfo1 15 }

outlet1WarnStatPDU5 OBJECT-TYPE
SYNTAX INTEGER (0..127)
ACCESS read-only
STATUS optional
DESCRIPTION
        " "
::= { baseinfo1 16 }

outlet2WarnStatPDU5 OBJECT-TYPE
SYNTAX INTEGER (0..127)
ACCESS read-only
STATUS optional
DESCRIPTION
        " "
::= { baseinfo1 17 }

outlet3WarnStatPDU5 OBJECT-TYPE
SYNTAX INTEGER (0..127)
ACCESS read-only
STATUS optional
DESCRIPTION
        " "
::= { baseinfo1 18 }

outlet4WarnStatPDU5 OBJECT-TYPE
SYNTAX INTEGER (0..127)
ACCESS read-only
STATUS optional
DESCRIPTION
        " "
::= { baseinfo1 19 }

outlet5WarnStatPDU5 OBJECT-TYPE
SYNTAX INTEGER (0..127)
ACCESS read-only
STATUS optional
DESCRIPTION
        " "
::= { baseinfo1 20 }

outlet6WarnStatPDU5 OBJECT-TYPE
SYNTAX INTEGER (0..127)
ACCESS read-only
STATUS optional
DESCRIPTION
        " "
::= { baseinfo1 21 }

outlet7WarnStatPDU5 OBJECT-TYPE
SYNTAX INTEGER (0..127)
ACCESS read-only
STATUS optional
DESCRIPTION
        " "
::= { baseinfo1 22 }

outlet8WarnStatPDU5 OBJECT-TYPE
SYNTAX INTEGER (0..127)
ACCESS read-only
STATUS optional
DESCRIPTION
        " "
::= { baseinfo1 23 }

outlet9WarnStatPDU5 OBJECT-TYPE
SYNTAX INTEGER (0..127)
ACCESS read-only
STATUS optional
DESCRIPTION
        " "
::= { baseinfo1 24 }

outlet10WarnStatPDU5 OBJECT-TYPE
SYNTAX INTEGER (0..127)
ACCESS read-only
STATUS optional
DESCRIPTION
        " "
::= { baseinfo1 25 }

outlet11WarnStatPDU5 OBJECT-TYPE
SYNTAX INTEGER (0..127)
ACCESS read-only
STATUS optional
DESCRIPTION
        " "
::= { baseinfo1 26 }

outlet12WarnStatPDU5 OBJECT-TYPE
SYNTAX INTEGER (0..127)
ACCESS read-only
STATUS optional
DESCRIPTION
        " "
::= { baseinfo1 27 }

outlet13WarnStatPDU5 OBJECT-TYPE
SYNTAX INTEGER (0..127)
ACCESS read-only
STATUS optional
DESCRIPTION
        " "
::= { baseinfo1 28 }

outlet14WarnStatPDU5 OBJECT-TYPE
SYNTAX INTEGER (0..127)
ACCESS read-only
STATUS optional
DESCRIPTION
        " "
::= { baseinfo1 29 }

outlet15WarnStatPDU5 OBJECT-TYPE
SYNTAX INTEGER (0..127)
ACCESS read-only
STATUS optional
DESCRIPTION
        " "
::= { baseinfo1 30 }

outlet16WarnStatPDU5 OBJECT-TYPE
SYNTAX INTEGER (0..127)
ACCESS read-only
STATUS optional
DESCRIPTION
        " "
::= { baseinfo1 31 }

outlet17WarnStatPDU5 OBJECT-TYPE
SYNTAX INTEGER (0..127)
ACCESS read-only
STATUS optional
DESCRIPTION
        " "
::= { baseinfo1 32 }

outlet18WarnStatPDU5 OBJECT-TYPE
SYNTAX INTEGER (0..127)
ACCESS read-only
STATUS optional
DESCRIPTION
        " "
::= { baseinfo1 33 }

outlet19WarnStatPDU5 OBJECT-TYPE
SYNTAX INTEGER (0..127)
ACCESS read-only
STATUS optional
DESCRIPTION
        " "
::= { baseinfo1 34 }

outlet20WarnStatPDU5 OBJECT-TYPE
SYNTAX INTEGER (0..127)
ACCESS read-only
STATUS optional
DESCRIPTION
        " "
::= { baseinfo1 35 }

outlet21WarnStatPDU5 OBJECT-TYPE
SYNTAX INTEGER (0..127)
ACCESS read-only
STATUS optional
DESCRIPTION
        " "
::= { baseinfo1 36 }

outlet22WarnStatPDU5 OBJECT-TYPE
SYNTAX INTEGER (0..127)
ACCESS read-only
STATUS optional
DESCRIPTION
        " "
::= { baseinfo1 37 }

outlet23WarnStatPDU5 OBJECT-TYPE
SYNTAX INTEGER (0..127)
ACCESS read-only
STATUS optional
DESCRIPTION
        " "
::= { baseinfo1 38 }

outlet24WarnStatPDU5 OBJECT-TYPE
SYNTAX INTEGER (0..127)
ACCESS read-only
STATUS optional
DESCRIPTION
        " "
::= { baseinfo1 39 }

outlet25WarnStatPDU5 OBJECT-TYPE
SYNTAX INTEGER (0..127)
ACCESS read-only
STATUS optional
DESCRIPTION
        " "
::= { baseinfo1 40 }

outlet26WarnStatPDU5 OBJECT-TYPE
SYNTAX INTEGER (0..127)
ACCESS read-only
STATUS optional
DESCRIPTION
        " "
::= { baseinfo1 41 }

outlet27WarnStatPDU5 OBJECT-TYPE
SYNTAX INTEGER (0..127)
ACCESS read-only
STATUS optional
DESCRIPTION
        " "
::= { baseinfo1 42 }

outlet28WarnStatPDU5 OBJECT-TYPE
SYNTAX INTEGER (0..127)
ACCESS read-only
STATUS optional
DESCRIPTION
        " "
::= { baseinfo1 43 }

outlet29WarnStatPDU5 OBJECT-TYPE
SYNTAX INTEGER (0..127)
ACCESS read-only
STATUS optional
DESCRIPTION
        " "
::= { baseinfo1 44 }

outlet30WarnStatPDU5 OBJECT-TYPE
SYNTAX INTEGER (0..127)
ACCESS read-only
STATUS optional
DESCRIPTION
        " "
::= { baseinfo1 45 }

outlet31WarnStatPDU5 OBJECT-TYPE
SYNTAX INTEGER (0..127)
ACCESS read-only
STATUS optional
DESCRIPTION
        " "
::= { baseinfo1 46 }

outlet32WarnStatPDU5 OBJECT-TYPE
SYNTAX INTEGER (0..127)
ACCESS read-only
STATUS optional
DESCRIPTION
        " "
::= { baseinfo1 47 }

outlet33WarnStatPDU5 OBJECT-TYPE
SYNTAX INTEGER (0..127)
ACCESS read-only
STATUS optional
DESCRIPTION
        " "
::= { baseinfo1 48 }

outlet34WarnStatPDU5 OBJECT-TYPE
SYNTAX INTEGER (0..127)
ACCESS read-only
STATUS optional
DESCRIPTION
        " "
::= { baseinfo1 49 }

outlet35WarnStatPDU5 OBJECT-TYPE
SYNTAX INTEGER (0..127)
ACCESS read-only
STATUS optional
DESCRIPTION
        " "
::= { baseinfo1 50 }

outlet36WarnStatPDU5 OBJECT-TYPE
SYNTAX INTEGER (0..127)
ACCESS read-only
STATUS optional
DESCRIPTION
        " "
::= { baseinfo1 51 }

input1 OBJECT IDENTIFIER ::= { pdu5 2 }

currentL1PDU5 OBJECT-TYPE
SYNTAX INTEGER (0..65535)
ACCESS read-only
STATUS optional
DESCRIPTION
        " "
::= { input1 1 }

voltageL1PDU5 OBJECT-TYPE
SYNTAX INTEGER (0..65535)
ACCESS read-only
STATUS optional
DESCRIPTION
        " "
::= { input1 2 }

powerL1PDU5 OBJECT-TYPE
SYNTAX INTEGER (0..65535)
ACCESS read-only
STATUS optional
DESCRIPTION
        " "
::= { input1 3 }

pfL1PDU5 OBJECT-TYPE
SYNTAX INTEGER (0..65535)
ACCESS read-only
STATUS optional
DESCRIPTION
        " "
::= { input1 4 }

energyL1PDU5 OBJECT-TYPE
SYNTAX INTEGER (0..65535)
ACCESS read-only
STATUS optional
DESCRIPTION
        " "
::= { input1 5 }

currentL2PDU5 OBJECT-TYPE
SYNTAX INTEGER (0..65535)
ACCESS read-only
STATUS optional
DESCRIPTION
        " "
::= { input1 6 }

voltageL2PDU5 OBJECT-TYPE
SYNTAX INTEGER (0..65535)
ACCESS read-only
STATUS optional
DESCRIPTION
        " "
::= { input1 7 }

powerL2PDU5 OBJECT-TYPE
SYNTAX INTEGER (0..65535)
ACCESS read-only
STATUS optional
DESCRIPTION
        " "
::= { input1 8 }

pfL2PDU5 OBJECT-TYPE
SYNTAX INTEGER (0..65535)
ACCESS read-only
STATUS optional
DESCRIPTION
        " "
::= { input1 9 }

energyL2PDU5 OBJECT-TYPE
SYNTAX INTEGER (0..65535)
ACCESS read-only
STATUS optional
DESCRIPTION
        " "
::= { input1 10 }

currentL3PDU5 OBJECT-TYPE
SYNTAX INTEGER (0..65535)
ACCESS read-only
STATUS optional
DESCRIPTION
        " "
::= { input1 11 }

voltageL3PDU5 OBJECT-TYPE
SYNTAX INTEGER (0..65535)
ACCESS read-only
STATUS optional
DESCRIPTION
        " "
::= { input1 12 }

powerL3PDU5 OBJECT-TYPE
SYNTAX INTEGER (0..65535)
ACCESS read-only
STATUS optional
DESCRIPTION
        " "
::= { input1 13 }

pfL3PDU5 OBJECT-TYPE
SYNTAX INTEGER (0..65535)
ACCESS read-only
STATUS optional
DESCRIPTION
        " "
::= { input1 14 }

energyL3PDU5 OBJECT-TYPE
SYNTAX INTEGER (0..65535)
ACCESS read-only
STATUS optional
DESCRIPTION
        " "
::= { input1 15 }

outletinfo1 OBJECT IDENTIFIER ::= { pdu5 3 }

outlet1PDU5 OBJECT IDENTIFIER ::= { outletinfo1 1 }

outlet2PDU5 OBJECT IDENTIFIER ::= { outletinfo1 2 }

outlet3PDU5 OBJECT IDENTIFIER ::= { outletinfo1 3 }

outlet4PDU5 OBJECT IDENTIFIER ::= { outletinfo1 4 }

outlet5PDU5 OBJECT IDENTIFIER ::= { outletinfo1 5 }

outlet6PDU5 OBJECT IDENTIFIER ::= { outletinfo1 6 }

outlet7PDU5 OBJECT IDENTIFIER ::= { outletinfo1 7 }

outlet8PDU5 OBJECT IDENTIFIER ::= { outletinfo1 8 }

outlet9PDU5 OBJECT IDENTIFIER ::= { outletinfo1 9 }

outlet10PDU5 OBJECT IDENTIFIER ::= { outletinfo1 10 }

outlet11PDU5 OBJECT IDENTIFIER ::= { outletinfo1 11 }

outlet12PDU5 OBJECT IDENTIFIER ::= { outletinfo1 12 }

outlet13PDU5 OBJECT IDENTIFIER ::= { outletinfo1 13 }

outlet14PDU5 OBJECT IDENTIFIER ::= { outletinfo1 14 }

outlet15PDU5 OBJECT IDENTIFIER ::= { outletinfo1 15 }

outlet16PDU5 OBJECT IDENTIFIER ::= { outletinfo1 16 }

outlet17PDU5 OBJECT IDENTIFIER ::= { outletinfo1 17 }

outlet18PDU5 OBJECT IDENTIFIER ::= { outletinfo1 18 }

outlet19PDU5 OBJECT IDENTIFIER ::= { outletinfo1 19 }

outlet20PDU5 OBJECT IDENTIFIER ::= { outletinfo1 20 }

outlet21PDU5 OBJECT IDENTIFIER ::= { outletinfo1 21 }

outlet22PDU5 OBJECT IDENTIFIER ::= { outletinfo1 22 }

outlet23PDU5 OBJECT IDENTIFIER ::= { outletinfo1 23 }

outlet24PDU5 OBJECT IDENTIFIER ::= { outletinfo1 24 }

outlet25PDU5 OBJECT IDENTIFIER ::= { outletinfo1 25 }

outlet26PDU5 OBJECT IDENTIFIER ::= { outletinfo1 26 }

outlet27PDU5 OBJECT IDENTIFIER ::= { outletinfo1 27 }

outlet28PDU5 OBJECT IDENTIFIER ::= { outletinfo1 28 }

outlet29PDU5 OBJECT IDENTIFIER ::= { outletinfo1 29 }

outlet30PDU5 OBJECT IDENTIFIER ::= { outletinfo1 30 }

outlet31PDU5 OBJECT IDENTIFIER ::= { outletinfo1 31 }

outlet32PDU5 OBJECT IDENTIFIER ::= { outletinfo1 32 }

outlet33PDU5 OBJECT IDENTIFIER ::= { outletinfo1 33 }

outlet34PDU5 OBJECT IDENTIFIER ::= { outletinfo1 34 }

outlet35PDU5 OBJECT IDENTIFIER ::= { outletinfo1 35 }

outlet36PDU5 OBJECT IDENTIFIER ::= { outletinfo1 36 }

switch1PDU5 OBJECT-TYPE
SYNTAX INTEGER (0..3)
ACCESS read-write
STATUS optional
DESCRIPTION
        " "
::= { outlet1PDU5 1 }

voltage1PDU5 OBJECT-TYPE
SYNTAX INTEGER (0..65535)
ACCESS read-only
STATUS optional
DESCRIPTION
        " "
::= { outlet1PDU5 2 }

current1PDU5 OBJECT-TYPE
SYNTAX INTEGER (0..65535)
ACCESS read-only
STATUS optional
DESCRIPTION
        " "
::= { outlet1PDU5 3 }

power1PDU5 OBJECT-TYPE
SYNTAX INTEGER (0..65535)
ACCESS read-only
STATUS optional
DESCRIPTION
        " "
::= { outlet1PDU5 4 }

pf1PDU5 OBJECT-TYPE
SYNTAX INTEGER (0..65535)
ACCESS read-only
STATUS optional
DESCRIPTION
        " "
::= { outlet1PDU5 5 }

energy1PDU5 OBJECT-TYPE
SYNTAX INTEGER (0..65535)
ACCESS read-only
STATUS optional
DESCRIPTION
        " "
::= { outlet1PDU5 6 }

switch2PDU5 OBJECT-TYPE
SYNTAX INTEGER (0..3)
ACCESS read-write
STATUS optional
DESCRIPTION
        " "
::= { outlet2PDU5 1 }

voltage2PDU5 OBJECT-TYPE
SYNTAX INTEGER (0..65535)
ACCESS read-only
STATUS optional
DESCRIPTION
        " "
::= { outlet2PDU5 2 }

current2PDU5 OBJECT-TYPE
SYNTAX INTEGER (0..65535)
ACCESS read-only
STATUS optional
DESCRIPTION
        " "
::= { outlet2PDU5 3 }

power2PDU5 OBJECT-TYPE
SYNTAX INTEGER (0..65535)
ACCESS read-only
STATUS optional
DESCRIPTION
        " "
::= { outlet2PDU5 4 }

pf2PDU5 OBJECT-TYPE
SYNTAX INTEGER (0..65535)
ACCESS read-only
STATUS optional
DESCRIPTION
        " "
::= { outlet2PDU5 5 }

energy2PDU5 OBJECT-TYPE
SYNTAX INTEGER (0..65535)
ACCESS read-only
STATUS optional
DESCRIPTION
        " "
::= { outlet2PDU5 6 }

switch3PDU5 OBJECT-TYPE
SYNTAX INTEGER (0..3)
ACCESS read-write
STATUS optional
DESCRIPTION
        " "
::= { outlet3PDU5 1 }

voltage3PDU5 OBJECT-TYPE
SYNTAX INTEGER (0..65535)
ACCESS read-only
STATUS optional
DESCRIPTION
        " "
::= { outlet3PDU5 2 }

current3PDU5 OBJECT-TYPE
SYNTAX INTEGER (0..65535)
ACCESS read-only
STATUS optional
DESCRIPTION
        " "
::= { outlet3PDU5 3 }

power3PDU5 OBJECT-TYPE
SYNTAX INTEGER (0..65535)
ACCESS read-only
STATUS optional
DESCRIPTION
        " "
::= { outlet3PDU5 4 }

pf3PDU5 OBJECT-TYPE
SYNTAX INTEGER (0..65535)
ACCESS read-only
STATUS optional
DESCRIPTION
        " "
::= { outlet3PDU5 5 }

energy3PDU5 OBJECT-TYPE
SYNTAX INTEGER (0..65535)
ACCESS read-only
STATUS optional
DESCRIPTION
        " "
::= { outlet3PDU5 6 }

switch4PDU5 OBJECT-TYPE
SYNTAX INTEGER (0..3)
ACCESS read-write
STATUS optional
DESCRIPTION
        " "
::= { outlet4PDU5 1 }

voltage4PDU5 OBJECT-TYPE
SYNTAX INTEGER (0..65535)
ACCESS read-only
STATUS optional
DESCRIPTION
        " "
::= { outlet4PDU5 2 }

current4PDU5 OBJECT-TYPE
SYNTAX INTEGER (0..65535)
ACCESS read-only
STATUS optional
DESCRIPTION
        " "
::= { outlet4PDU5 3 }

power4PDU5 OBJECT-TYPE
SYNTAX INTEGER (0..65535)
ACCESS read-only
STATUS optional
DESCRIPTION
        " "
::= { outlet4PDU5 4 }

pf4PDU5 OBJECT-TYPE
SYNTAX INTEGER (0..65535)
ACCESS read-only
STATUS optional
DESCRIPTION
        " "
::= { outlet4PDU5 5 }

energy4PDU5 OBJECT-TYPE
SYNTAX INTEGER (0..65535)
ACCESS read-only
STATUS optional
DESCRIPTION
        " "
::= { outlet4PDU5 6 }

switch5PDU5 OBJECT-TYPE
SYNTAX INTEGER (0..3)
ACCESS read-write
STATUS optional
DESCRIPTION
        " "
::= { outlet5PDU5 1 }

voltage5PDU5 OBJECT-TYPE
SYNTAX INTEGER (0..65535)
ACCESS read-only
STATUS optional
DESCRIPTION
        " "
::= { outlet5PDU5 2 }

current5PDU5 OBJECT-TYPE
SYNTAX INTEGER (0..65535)
ACCESS read-only
STATUS optional
DESCRIPTION
        " "
::= { outlet5PDU5 3 }

power5PDU5 OBJECT-TYPE
SYNTAX INTEGER (0..65535)
ACCESS read-only
STATUS optional
DESCRIPTION
        " "
::= { outlet5PDU5 4 }

pf5PDU5 OBJECT-TYPE
SYNTAX INTEGER (0..65535)
ACCESS read-only
STATUS optional
DESCRIPTION
        " "
::= { outlet5PDU5 5 }

energy5PDU5 OBJECT-TYPE
SYNTAX INTEGER (0..65535)
ACCESS read-only
STATUS optional
DESCRIPTION
        " "
::= { outlet5PDU5 6 }

switch6PDU5 OBJECT-TYPE
SYNTAX INTEGER (0..3)
ACCESS read-write
STATUS optional
DESCRIPTION
        " "
::= { outlet6PDU5 1 }

voltage6PDU5 OBJECT-TYPE
SYNTAX INTEGER (0..65535)
ACCESS read-only
STATUS optional
DESCRIPTION
        " "
::= { outlet6PDU5 2 }

current6PDU5 OBJECT-TYPE
SYNTAX INTEGER (0..65535)
ACCESS read-only
STATUS optional
DESCRIPTION
        " "
::= { outlet6PDU5 3 }

power6PDU5 OBJECT-TYPE
SYNTAX INTEGER (0..65535)
ACCESS read-only
STATUS optional
DESCRIPTION
        " "
::= { outlet6PDU5 4 }

pf6PDU5 OBJECT-TYPE
SYNTAX INTEGER (0..65535)
ACCESS read-only
STATUS optional
DESCRIPTION
        " "
::= { outlet6PDU5 5 }

energy6PDU5 OBJECT-TYPE
SYNTAX INTEGER (0..65535)
ACCESS read-only
STATUS optional
DESCRIPTION
        " "
::= { outlet6PDU5 6 }

switch7PDU5 OBJECT-TYPE
SYNTAX INTEGER (0..3)
ACCESS read-write
STATUS optional
DESCRIPTION
        " "
::= { outlet7PDU5 1 }

voltage7PDU5 OBJECT-TYPE
SYNTAX INTEGER (0..65535)
ACCESS read-only
STATUS optional
DESCRIPTION
        " "
::= { outlet7PDU5 2 }

current7PDU5 OBJECT-TYPE
SYNTAX INTEGER (0..65535)
ACCESS read-only
STATUS optional
DESCRIPTION
        " "
::= { outlet7PDU5 3 }

power7PDU5 OBJECT-TYPE
SYNTAX INTEGER (0..65535)
ACCESS read-only
STATUS optional
DESCRIPTION
        " "
::= { outlet7PDU5 4 }

pf7PDU5 OBJECT-TYPE
SYNTAX INTEGER (0..65535)
ACCESS read-only
STATUS optional
DESCRIPTION
        " "
::= { outlet7PDU5 5 }

energy7PDU5 OBJECT-TYPE
SYNTAX INTEGER (0..65535)
ACCESS read-only
STATUS optional
DESCRIPTION
        " "
::= { outlet7PDU5 6 }

switch8PDU5 OBJECT-TYPE
SYNTAX INTEGER (0..3)
ACCESS read-write
STATUS optional
DESCRIPTION
        " "
::= { outlet8PDU5 1 }

voltage8PDU5 OBJECT-TYPE
SYNTAX INTEGER (0..65535)
ACCESS read-only
STATUS optional
DESCRIPTION
        " "
::= { outlet8PDU5 2 }

current8PDU5 OBJECT-TYPE
SYNTAX INTEGER (0..65535)
ACCESS read-only
STATUS optional
DESCRIPTION
        " "
::= { outlet8PDU5 3 }

power8PDU5 OBJECT-TYPE
SYNTAX INTEGER (0..65535)
ACCESS read-only
STATUS optional
DESCRIPTION
        " "
::= { outlet8PDU5 4 }

pf8PDU5 OBJECT-TYPE
SYNTAX INTEGER (0..65535)
ACCESS read-only
STATUS optional
DESCRIPTION
        " "
::= { outlet8PDU5 5 }

energy8PDU5 OBJECT-TYPE
SYNTAX INTEGER (0..65535)
ACCESS read-only
STATUS optional
DESCRIPTION
        " "
::= { outlet8PDU5 6 }

switch9PDU5 OBJECT-TYPE
SYNTAX INTEGER (0..3)
ACCESS read-write
STATUS optional
DESCRIPTION
        " "
::= { outlet9PDU5 1 }

voltage9PDU5 OBJECT-TYPE
SYNTAX INTEGER (0..65535)
ACCESS read-only
STATUS optional
DESCRIPTION
        " "
::= { outlet9PDU5 2 }

current9PDU5 OBJECT-TYPE
SYNTAX INTEGER (0..65535)
ACCESS read-only
STATUS optional
DESCRIPTION
        " "
::= { outlet9PDU5 3 }

power9PDU5 OBJECT-TYPE
SYNTAX INTEGER (0..65535)
ACCESS read-only
STATUS optional
DESCRIPTION
        " "
::= { outlet9PDU5 4 }

pf9PDU5 OBJECT-TYPE
SYNTAX INTEGER (0..65535)
ACCESS read-only
STATUS optional
DESCRIPTION
        " "
::= { outlet9PDU5 5 }

energy9PDU5 OBJECT-TYPE
SYNTAX INTEGER (0..65535)
ACCESS read-only
STATUS optional
DESCRIPTION
        " "
::= { outlet9PDU5 6 }

switch10PDU5 OBJECT-TYPE
SYNTAX INTEGER (0..3)
ACCESS read-write
STATUS optional
DESCRIPTION
        " "
::= { outlet10PDU5 1 }

voltage10PDU5 OBJECT-TYPE
SYNTAX INTEGER (0..65535)
ACCESS read-only
STATUS optional
DESCRIPTION
        " "
::= { outlet10PDU5 2 }

current10PDU5 OBJECT-TYPE
SYNTAX INTEGER (0..65535)
ACCESS read-only
STATUS optional
DESCRIPTION
        " "
::= { outlet10PDU5 3 }

power10PDU5 OBJECT-TYPE
SYNTAX INTEGER (0..65535)
ACCESS read-only
STATUS optional
DESCRIPTION
        " "
::= { outlet10PDU5 4 }

pf10PDU5 OBJECT-TYPE
SYNTAX INTEGER (0..65535)
ACCESS read-only
STATUS optional
DESCRIPTION
        " "
::= { outlet10PDU5 5 }

energy10PDU5 OBJECT-TYPE
SYNTAX INTEGER (0..65535)
ACCESS read-only
STATUS optional
DESCRIPTION
        " "
::= { outlet10PDU5 6 }

switch11PDU5 OBJECT-TYPE
SYNTAX INTEGER (0..3)
ACCESS read-write
STATUS optional
DESCRIPTION
        " "
::= { outlet11PDU5 1 }

voltage11PDU5 OBJECT-TYPE
SYNTAX INTEGER (0..65535)
ACCESS read-only
STATUS optional
DESCRIPTION
        " "
::= { outlet11PDU5 2 }

current11PDU5 OBJECT-TYPE
SYNTAX INTEGER (0..65535)
ACCESS read-only
STATUS optional
DESCRIPTION
        " "
::= { outlet11PDU5 3 }

power11PDU5 OBJECT-TYPE
SYNTAX INTEGER (0..65535)
ACCESS read-only
STATUS optional
DESCRIPTION
        " "
::= { outlet11PDU5 4 }

pf11PDU5 OBJECT-TYPE
SYNTAX INTEGER (0..65535)
ACCESS read-only
STATUS optional
DESCRIPTION
        " "
::= { outlet11PDU5 5 }

energy11PDU5 OBJECT-TYPE
SYNTAX INTEGER (0..65535)
ACCESS read-only
STATUS optional
DESCRIPTION
        " "
::= { outlet11PDU5 6 }

switch12PDU5 OBJECT-TYPE
SYNTAX INTEGER (0..3)
ACCESS read-write
STATUS optional
DESCRIPTION
        " "
::= { outlet12PDU5 1 }

voltage12PDU5 OBJECT-TYPE
SYNTAX INTEGER (0..65535)
ACCESS read-only
STATUS optional
DESCRIPTION
        " "
::= { outlet12PDU5 2 }

current12PDU5 OBJECT-TYPE
SYNTAX INTEGER (0..65535)
ACCESS read-only
STATUS optional
DESCRIPTION
        " "
::= { outlet12PDU5 3 }

power12PDU5 OBJECT-TYPE
SYNTAX INTEGER (0..65535)
ACCESS read-only
STATUS optional
DESCRIPTION
        " "
::= { outlet12PDU5 4 }

pf12PDU5 OBJECT-TYPE
SYNTAX INTEGER (0..65535)
ACCESS read-only
STATUS optional
DESCRIPTION
        " "
::= { outlet12PDU5 5 }

energy12PDU5 OBJECT-TYPE
SYNTAX INTEGER (0..65535)
ACCESS read-only
STATUS optional
DESCRIPTION
        " "
::= { outlet12PDU5 6 }

switch13PDU5 OBJECT-TYPE
SYNTAX INTEGER (0..3)
ACCESS read-write
STATUS optional
DESCRIPTION
        " "
::= { outlet13PDU5 1 }

voltage13PDU5 OBJECT-TYPE
SYNTAX INTEGER (0..65535)
ACCESS read-only
STATUS optional
DESCRIPTION
        " "
::= { outlet13PDU5 2 }

current13PDU5 OBJECT-TYPE
SYNTAX INTEGER (0..65535)
ACCESS read-only
STATUS optional
DESCRIPTION
        " "
::= { outlet13PDU5 3 }

power13PDU5 OBJECT-TYPE
SYNTAX INTEGER (0..65535)
ACCESS read-only
STATUS optional
DESCRIPTION
        " "
::= { outlet13PDU5 4 }

pf13PDU5 OBJECT-TYPE
SYNTAX INTEGER (0..65535)
ACCESS read-only
STATUS optional
DESCRIPTION
        " "
::= { outlet13PDU5 5 }

energy13PDU5 OBJECT-TYPE
SYNTAX INTEGER (0..65535)
ACCESS read-only
STATUS optional
DESCRIPTION
        " "
::= { outlet13PDU5 6 }

switch14PDU5 OBJECT-TYPE
SYNTAX INTEGER (0..3)
ACCESS read-write
STATUS optional
DESCRIPTION
        " "
::= { outlet14PDU5 1 }

voltage14PDU5 OBJECT-TYPE
SYNTAX INTEGER (0..65535)
ACCESS read-only
STATUS optional
DESCRIPTION
        " "
::= { outlet14PDU5 2 }

current14PDU5 OBJECT-TYPE
SYNTAX INTEGER (0..65535)
ACCESS read-only
STATUS optional
DESCRIPTION
        " "
::= { outlet14PDU5 3 }

power14PDU5 OBJECT-TYPE
SYNTAX INTEGER (0..65535)
ACCESS read-only
STATUS optional
DESCRIPTION
        " "
::= { outlet14PDU5 4 }

pf14PDU5 OBJECT-TYPE
SYNTAX INTEGER (0..65535)
ACCESS read-only
STATUS optional
DESCRIPTION
        " "
::= { outlet14PDU5 5 }

energy14PDU5 OBJECT-TYPE
SYNTAX INTEGER (0..65535)
ACCESS read-only
STATUS optional
DESCRIPTION
        " "
::= { outlet14PDU5 6 }

switch15PDU5 OBJECT-TYPE
SYNTAX INTEGER (0..3)
ACCESS read-write
STATUS optional
DESCRIPTION
        " "
::= { outlet15PDU5 1 }

voltage15PDU5 OBJECT-TYPE
SYNTAX INTEGER (0..65535)
ACCESS read-only
STATUS optional
DESCRIPTION
        " "
::= { outlet15PDU5 2 }

current15PDU5 OBJECT-TYPE
SYNTAX INTEGER (0..65535)
ACCESS read-only
STATUS optional
DESCRIPTION
        " "
::= { outlet15PDU5 3 }

power15PDU5 OBJECT-TYPE
SYNTAX INTEGER (0..65535)
ACCESS read-only
STATUS optional
DESCRIPTION
        " "
::= { outlet15PDU5 4 }

pf15PDU5 OBJECT-TYPE
SYNTAX INTEGER (0..65535)
ACCESS read-only
STATUS optional
DESCRIPTION
        " "
::= { outlet15PDU5 5 }

energy15PDU5 OBJECT-TYPE
SYNTAX INTEGER (0..65535)
ACCESS read-only
STATUS optional
DESCRIPTION
        " "
::= { outlet15PDU5 6 }

switch16PDU5 OBJECT-TYPE
SYNTAX INTEGER (0..3)
ACCESS read-write
STATUS optional
DESCRIPTION
        " "
::= { outlet16PDU5 1 }

voltage16PDU5 OBJECT-TYPE
SYNTAX INTEGER (0..65535)
ACCESS read-only
STATUS optional
DESCRIPTION
        " "
::= { outlet16PDU5 2 }

current16PDU5 OBJECT-TYPE
SYNTAX INTEGER (0..65535)
ACCESS read-only
STATUS optional
DESCRIPTION
        " "
::= { outlet16PDU5 3 }

power16PDU5 OBJECT-TYPE
SYNTAX INTEGER (0..65535)
ACCESS read-only
STATUS optional
DESCRIPTION
        " "
::= { outlet16PDU5 4 }

pf16PDU5 OBJECT-TYPE
SYNTAX INTEGER (0..65535)
ACCESS read-only
STATUS optional
DESCRIPTION
        " "
::= { outlet16PDU5 5 }

energy16PDU5 OBJECT-TYPE
SYNTAX INTEGER (0..65535)
ACCESS read-only
STATUS optional
DESCRIPTION
        " "
::= { outlet16PDU5 6 }

switch17PDU5 OBJECT-TYPE
SYNTAX INTEGER (0..3)
ACCESS read-write
STATUS optional
DESCRIPTION
        " "
::= { outlet17PDU5 1 }

voltage17PDU5 OBJECT-TYPE
SYNTAX INTEGER (0..65535)
ACCESS read-only
STATUS optional
DESCRIPTION
        " "
::= { outlet17PDU5 2 }

current17PDU5 OBJECT-TYPE
SYNTAX INTEGER (0..65535)
ACCESS read-only
STATUS optional
DESCRIPTION
        " "
::= { outlet17PDU5 3 }

power17PDU5 OBJECT-TYPE
SYNTAX INTEGER (0..65535)
ACCESS read-only
STATUS optional
DESCRIPTION
        " "
::= { outlet17PDU5 4 }

pf17PDU5 OBJECT-TYPE
SYNTAX INTEGER (0..65535)
ACCESS read-only
STATUS optional
DESCRIPTION
        " "
::= { outlet17PDU5 5 }

energy17PDU5 OBJECT-TYPE
SYNTAX INTEGER (0..65535)
ACCESS read-only
STATUS optional
DESCRIPTION
        " "
::= { outlet17PDU5 6 }

switch18PDU5 OBJECT-TYPE
SYNTAX INTEGER (0..3)
ACCESS read-write
STATUS optional
DESCRIPTION
        " "
::= { outlet18PDU5 1 }

voltage18PDU5 OBJECT-TYPE
SYNTAX INTEGER (0..65535)
ACCESS read-only
STATUS optional
DESCRIPTION
        " "
::= { outlet18PDU5 2 }

current18PDU5 OBJECT-TYPE
SYNTAX INTEGER (0..65535)
ACCESS read-only
STATUS optional
DESCRIPTION
        " "
::= { outlet18PDU5 3 }

power18PDU5 OBJECT-TYPE
SYNTAX INTEGER (0..65535)
ACCESS read-only
STATUS optional
DESCRIPTION
        " "
::= { outlet18PDU5 4 }

pf18PDU5 OBJECT-TYPE
SYNTAX INTEGER (0..65535)
ACCESS read-only
STATUS optional
DESCRIPTION
        " "
::= { outlet18PDU5 5 }

energy18PDU5 OBJECT-TYPE
SYNTAX INTEGER (0..65535)
ACCESS read-only
STATUS optional
DESCRIPTION
        " "
::= { outlet18PDU5 6 }

switch19PDU5 OBJECT-TYPE
SYNTAX INTEGER (0..3)
ACCESS read-write
STATUS optional
DESCRIPTION
        " "
::= { outlet19PDU5 1 }

voltage19PDU5 OBJECT-TYPE
SYNTAX INTEGER (0..65535)
ACCESS read-only
STATUS optional
DESCRIPTION
        " "
::= { outlet19PDU5 2 }

current19PDU5 OBJECT-TYPE
SYNTAX INTEGER (0..65535)
ACCESS read-only
STATUS optional
DESCRIPTION
        " "
::= { outlet19PDU5 3 }

power19PDU5 OBJECT-TYPE
SYNTAX INTEGER (0..65535)
ACCESS read-only
STATUS optional
DESCRIPTION
        " "
::= { outlet19PDU5 4 }

pf19PDU5 OBJECT-TYPE
SYNTAX INTEGER (0..65535)
ACCESS read-only
STATUS optional
DESCRIPTION
        " "
::= { outlet19PDU5 5 }

energy19PDU5 OBJECT-TYPE
SYNTAX INTEGER (0..65535)
ACCESS read-only
STATUS optional
DESCRIPTION
        " "
::= { outlet19PDU5 6 }

switch20PDU5 OBJECT-TYPE
SYNTAX INTEGER (0..3)
ACCESS read-write
STATUS optional
DESCRIPTION
        " "
::= { outlet20PDU5 1 }

voltage20PDU5 OBJECT-TYPE
SYNTAX INTEGER (0..65535)
ACCESS read-only
STATUS optional
DESCRIPTION
        " "
::= { outlet20PDU5 2 }

current20PDU5 OBJECT-TYPE
SYNTAX INTEGER (0..65535)
ACCESS read-only
STATUS optional
DESCRIPTION
        " "
::= { outlet20PDU5 3 }

power20PDU5 OBJECT-TYPE
SYNTAX INTEGER (0..65535)
ACCESS read-only
STATUS optional
DESCRIPTION
        " "
::= { outlet20PDU5 4 }

pf20PDU5 OBJECT-TYPE
SYNTAX INTEGER (0..65535)
ACCESS read-only
STATUS optional
DESCRIPTION
        " "
::= { outlet20PDU5 5 }

energy20PDU5 OBJECT-TYPE
SYNTAX INTEGER (0..65535)
ACCESS read-only
STATUS optional
DESCRIPTION
        " "
::= { outlet20PDU5 6 }

switch21PDU5 OBJECT-TYPE
SYNTAX INTEGER (0..3)
ACCESS read-write
STATUS optional
DESCRIPTION
        " "
::= { outlet21PDU5 1 }

voltage21PDU5 OBJECT-TYPE
SYNTAX INTEGER (0..65535)
ACCESS read-only
STATUS optional
DESCRIPTION
        " "
::= { outlet21PDU5 2 }

current21PDU5 OBJECT-TYPE
SYNTAX INTEGER (0..65535)
ACCESS read-only
STATUS optional
DESCRIPTION
        " "
::= { outlet21PDU5 3 }

power21PDU5 OBJECT-TYPE
SYNTAX INTEGER (0..65535)
ACCESS read-only
STATUS optional
DESCRIPTION
        " "
::= { outlet21PDU5 4 }

pf21PDU5 OBJECT-TYPE
SYNTAX INTEGER (0..65535)
ACCESS read-only
STATUS optional
DESCRIPTION
        " "
::= { outlet21PDU5 5 }

energy21PDU5 OBJECT-TYPE
SYNTAX INTEGER (0..65535)
ACCESS read-only
STATUS optional
DESCRIPTION
        " "
::= { outlet21PDU5 6 }

switch22PDU5 OBJECT-TYPE
SYNTAX INTEGER (0..3)
ACCESS read-write
STATUS optional
DESCRIPTION
        " "
::= { outlet22PDU5 1 }

voltage22PDU5 OBJECT-TYPE
SYNTAX INTEGER (0..65535)
ACCESS read-only
STATUS optional
DESCRIPTION
        " "
::= { outlet22PDU5 2 }

current22PDU5 OBJECT-TYPE
SYNTAX INTEGER (0..65535)
ACCESS read-only
STATUS optional
DESCRIPTION
        " "
::= { outlet22PDU5 3 }

power22PDU5 OBJECT-TYPE
SYNTAX INTEGER (0..65535)
ACCESS read-only
STATUS optional
DESCRIPTION
        " "
::= { outlet22PDU5 4 }

pf22PDU5 OBJECT-TYPE
SYNTAX INTEGER (0..65535)
ACCESS read-only
STATUS optional
DESCRIPTION
        " "
::= { outlet22PDU5 5 }

energy22PDU5 OBJECT-TYPE
SYNTAX INTEGER (0..65535)
ACCESS read-only
STATUS optional
DESCRIPTION
        " "
::= { outlet22PDU5 6 }

switch23PDU5 OBJECT-TYPE
SYNTAX INTEGER (0..3)
ACCESS read-write
STATUS optional
DESCRIPTION
        " "
::= { outlet23PDU5 1 }

voltage23PDU5 OBJECT-TYPE
SYNTAX INTEGER (0..65535)
ACCESS read-only
STATUS optional
DESCRIPTION
        " "
::= { outlet23PDU5 2 }

current23PDU5 OBJECT-TYPE
SYNTAX INTEGER (0..65535)
ACCESS read-only
STATUS optional
DESCRIPTION
        " "
::= { outlet23PDU5 3 }

power23PDU5 OBJECT-TYPE
SYNTAX INTEGER (0..65535)
ACCESS read-only
STATUS optional
DESCRIPTION
        " "
::= { outlet23PDU5 4 }

pf23PDU5 OBJECT-TYPE
SYNTAX INTEGER (0..65535)
ACCESS read-only
STATUS optional
DESCRIPTION
        " "
::= { outlet23PDU5 5 }

energy23PDU5 OBJECT-TYPE
SYNTAX INTEGER (0..65535)
ACCESS read-only
STATUS optional
DESCRIPTION
        " "
::= { outlet23PDU5 6 }

switch24PDU5 OBJECT-TYPE
SYNTAX INTEGER (0..3)
ACCESS read-write
STATUS optional
DESCRIPTION
        " "
::= { outlet24PDU5 1 }

voltage24PDU5 OBJECT-TYPE
SYNTAX INTEGER (0..65535)
ACCESS read-only
STATUS optional
DESCRIPTION
        " "
::= { outlet24PDU5 2 }

current24PDU5 OBJECT-TYPE
SYNTAX INTEGER (0..65535)
ACCESS read-only
STATUS optional
DESCRIPTION
        " "
::= { outlet24PDU5 3 }

power24PDU5 OBJECT-TYPE
SYNTAX INTEGER (0..65535)
ACCESS read-only
STATUS optional
DESCRIPTION
        " "
::= { outlet24PDU5 4 }

pf24PDU5 OBJECT-TYPE
SYNTAX INTEGER (0..65535)
ACCESS read-only
STATUS optional
DESCRIPTION
        " "
::= { outlet24PDU5 5 }

energy24PDU5 OBJECT-TYPE
SYNTAX INTEGER (0..65535)
ACCESS read-only
STATUS optional
DESCRIPTION
        " "
::= { outlet24PDU5 6 }

switch25PDU5 OBJECT-TYPE
SYNTAX INTEGER (0..3)
ACCESS read-write
STATUS optional
DESCRIPTION
        " "
::= { outlet25PDU5 1 }

voltage25PDU5 OBJECT-TYPE
SYNTAX INTEGER (0..65535)
ACCESS read-only
STATUS optional
DESCRIPTION
        " "
::= { outlet25PDU5 2 }

current25PDU5 OBJECT-TYPE
SYNTAX INTEGER (0..65535)
ACCESS read-only
STATUS optional
DESCRIPTION
        " "
::= { outlet25PDU5 3 }

power25PDU5 OBJECT-TYPE
SYNTAX INTEGER (0..65535)
ACCESS read-only
STATUS optional
DESCRIPTION
        " "
::= { outlet25PDU5 4 }

pf25PDU5 OBJECT-TYPE
SYNTAX INTEGER (0..65535)
ACCESS read-only
STATUS optional
DESCRIPTION
        " "
::= { outlet25PDU5 5 }

energy25PDU5 OBJECT-TYPE
SYNTAX INTEGER (0..65535)
ACCESS read-only
STATUS optional
DESCRIPTION
        " "
::= { outlet25PDU5 6 }

switch26PDU5 OBJECT-TYPE
SYNTAX INTEGER (0..3)
ACCESS read-write
STATUS optional
DESCRIPTION
        " "
::= { outlet26PDU5 1 }

voltage26PDU5 OBJECT-TYPE
SYNTAX INTEGER (0..65535)
ACCESS read-only
STATUS optional
DESCRIPTION
        " "
::= { outlet26PDU5 2 }

current26PDU5 OBJECT-TYPE
SYNTAX INTEGER (0..65535)
ACCESS read-only
STATUS optional
DESCRIPTION
        " "
::= { outlet26PDU5 3 }

power26PDU5 OBJECT-TYPE
SYNTAX INTEGER (0..65535)
ACCESS read-only
STATUS optional
DESCRIPTION
        " "
::= { outlet26PDU5 4 }

pf26PDU5 OBJECT-TYPE
SYNTAX INTEGER (0..65535)
ACCESS read-only
STATUS optional
DESCRIPTION
        " "
::= { outlet26PDU5 5 }

energy26PDU5 OBJECT-TYPE
SYNTAX INTEGER (0..65535)
ACCESS read-only
STATUS optional
DESCRIPTION
        " "
::= { outlet26PDU5 6 }

switch27PDU5 OBJECT-TYPE
SYNTAX INTEGER (0..3)
ACCESS read-write
STATUS optional
DESCRIPTION
        " "
::= { outlet27PDU5 1 }

voltage27PDU5 OBJECT-TYPE
SYNTAX INTEGER (0..65535)
ACCESS read-only
STATUS optional
DESCRIPTION
        " "
::= { outlet27PDU5 2 }

current27PDU5 OBJECT-TYPE
SYNTAX INTEGER (0..65535)
ACCESS read-only
STATUS optional
DESCRIPTION
        " "
::= { outlet27PDU5 3 }

power27PDU5 OBJECT-TYPE
SYNTAX INTEGER (0..65535)
ACCESS read-only
STATUS optional
DESCRIPTION
        " "
::= { outlet27PDU5 4 }

pf27PDU5 OBJECT-TYPE
SYNTAX INTEGER (0..65535)
ACCESS read-only
STATUS optional
DESCRIPTION
        " "
::= { outlet27PDU5 5 }

energy27PDU5 OBJECT-TYPE
SYNTAX INTEGER (0..65535)
ACCESS read-only
STATUS optional
DESCRIPTION
        " "
::= { outlet27PDU5 6 }

switch28PDU5 OBJECT-TYPE
SYNTAX INTEGER (0..3)
ACCESS read-write
STATUS optional
DESCRIPTION
        " "
::= { outlet28PDU5 1 }

voltage28PDU5 OBJECT-TYPE
SYNTAX INTEGER (0..65535)
ACCESS read-only
STATUS optional
DESCRIPTION
        " "
::= { outlet28PDU5 2 }

current28PDU5 OBJECT-TYPE
SYNTAX INTEGER (0..65535)
ACCESS read-only
STATUS optional
DESCRIPTION
        " "
::= { outlet28PDU5 3 }

power28PDU5 OBJECT-TYPE
SYNTAX INTEGER (0..65535)
ACCESS read-only
STATUS optional
DESCRIPTION
        " "
::= { outlet28PDU5 4 }

pf28PDU5 OBJECT-TYPE
SYNTAX INTEGER (0..65535)
ACCESS read-only
STATUS optional
DESCRIPTION
        " "
::= { outlet28PDU5 5 }

energy28PDU5 OBJECT-TYPE
SYNTAX INTEGER (0..65535)
ACCESS read-only
STATUS optional
DESCRIPTION
        " "
::= { outlet28PDU5 6 }

switch29PDU5 OBJECT-TYPE
SYNTAX INTEGER (0..3)
ACCESS read-write
STATUS optional
DESCRIPTION
        " "
::= { outlet29PDU5 1 }

voltage29PDU5 OBJECT-TYPE
SYNTAX INTEGER (0..65535)
ACCESS read-only
STATUS optional
DESCRIPTION
        " "
::= { outlet29PDU5 2 }

current29PDU5 OBJECT-TYPE
SYNTAX INTEGER (0..65535)
ACCESS read-only
STATUS optional
DESCRIPTION
        " "
::= { outlet29PDU5 3 }

power29PDU5 OBJECT-TYPE
SYNTAX INTEGER (0..65535)
ACCESS read-only
STATUS optional
DESCRIPTION
        " "
::= { outlet29PDU5 4 }

pf29PDU5 OBJECT-TYPE
SYNTAX INTEGER (0..65535)
ACCESS read-only
STATUS optional
DESCRIPTION
        " "
::= { outlet29PDU5 5 }

energy29PDU5 OBJECT-TYPE
SYNTAX INTEGER (0..65535)
ACCESS read-only
STATUS optional
DESCRIPTION
        " "
::= { outlet29PDU5 6 }

switch30PDU5 OBJECT-TYPE
SYNTAX INTEGER (0..3)
ACCESS read-write
STATUS optional
DESCRIPTION
        " "
::= { outlet30PDU5 1 }

voltage30PDU5 OBJECT-TYPE
SYNTAX INTEGER (0..65535)
ACCESS read-only
STATUS optional
DESCRIPTION
        " "
::= { outlet30PDU5 2 }

current30PDU5 OBJECT-TYPE
SYNTAX INTEGER (0..65535)
ACCESS read-only
STATUS optional
DESCRIPTION
        " "
::= { outlet30PDU5 3 }

power30PDU5 OBJECT-TYPE
SYNTAX INTEGER (0..65535)
ACCESS read-only
STATUS optional
DESCRIPTION
        " "
::= { outlet30PDU5 4 }

pf30PDU5 OBJECT-TYPE
SYNTAX INTEGER (0..65535)
ACCESS read-only
STATUS optional
DESCRIPTION
        " "
::= { outlet30PDU5 5 }

energy30PDU5 OBJECT-TYPE
SYNTAX INTEGER (0..65535)
ACCESS read-only
STATUS optional
DESCRIPTION
        " "
::= { outlet30PDU5 6 }

switch31PDU5 OBJECT-TYPE
SYNTAX INTEGER (0..3)
ACCESS read-write
STATUS optional
DESCRIPTION
        " "
::= { outlet31PDU5 1 }

voltage31PDU5 OBJECT-TYPE
SYNTAX INTEGER (0..65535)
ACCESS read-only
STATUS optional
DESCRIPTION
        " "
::= { outlet31PDU5 2 }

current31PDU5 OBJECT-TYPE
SYNTAX INTEGER (0..65535)
ACCESS read-only
STATUS optional
DESCRIPTION
        " "
::= { outlet31PDU5 3 }

power31PDU5 OBJECT-TYPE
SYNTAX INTEGER (0..65535)
ACCESS read-only
STATUS optional
DESCRIPTION
        " "
::= { outlet31PDU5 4 }

pf31PDU5 OBJECT-TYPE
SYNTAX INTEGER (0..65535)
ACCESS read-only
STATUS optional
DESCRIPTION
        " "
::= { outlet31PDU5 5 }

energy31PDU5 OBJECT-TYPE
SYNTAX INTEGER (0..65535)
ACCESS read-only
STATUS optional
DESCRIPTION
        " "
::= { outlet31PDU5 6 }

switch32PDU5 OBJECT-TYPE
SYNTAX INTEGER (0..3)
ACCESS read-write
STATUS optional
DESCRIPTION
        " "
::= { outlet32PDU5 1 }

voltage32PDU5 OBJECT-TYPE
SYNTAX INTEGER (0..65535)
ACCESS read-only
STATUS optional
DESCRIPTION
        " "
::= { outlet32PDU5 2 }

current32PDU5 OBJECT-TYPE
SYNTAX INTEGER (0..65535)
ACCESS read-only
STATUS optional
DESCRIPTION
        " "
::= { outlet32PDU5 3 }

power32PDU5 OBJECT-TYPE
SYNTAX INTEGER (0..65535)
ACCESS read-only
STATUS optional
DESCRIPTION
        " "
::= { outlet32PDU5 4 }

pf32PDU5 OBJECT-TYPE
SYNTAX INTEGER (0..65535)
ACCESS read-only
STATUS optional
DESCRIPTION
        " "
::= { outlet32PDU5 5 }

energy32PDU5 OBJECT-TYPE
SYNTAX INTEGER (0..65535)
ACCESS read-only
STATUS optional
DESCRIPTION
        " "
::= { outlet32PDU5 6 }

switch33PDU5 OBJECT-TYPE
SYNTAX INTEGER (0..3)
ACCESS read-write
STATUS optional
DESCRIPTION
        " "
::= { outlet33PDU5 1 }

voltage33PDU5 OBJECT-TYPE
SYNTAX INTEGER (0..65535)
ACCESS read-only
STATUS optional
DESCRIPTION
        " "
::= { outlet33PDU5 2 }

current33PDU5 OBJECT-TYPE
SYNTAX INTEGER (0..65535)
ACCESS read-only
STATUS optional
DESCRIPTION
        " "
::= { outlet33PDU5 3 }

power33PDU5 OBJECT-TYPE
SYNTAX INTEGER (0..65535)
ACCESS read-only
STATUS optional
DESCRIPTION
        " "
::= { outlet33PDU5 4 }

pf33PDU5 OBJECT-TYPE
SYNTAX INTEGER (0..65535)
ACCESS read-only
STATUS optional
DESCRIPTION
        " "
::= { outlet33PDU5 5 }

energy33PDU5 OBJECT-TYPE
SYNTAX INTEGER (0..65535)
ACCESS read-only
STATUS optional
DESCRIPTION
        " "
::= { outlet33PDU5 6 }

switch34PDU5 OBJECT-TYPE
SYNTAX INTEGER (0..3)
ACCESS read-write
STATUS optional
DESCRIPTION
        " "
::= { outlet34PDU5 1 }

voltage34PDU5 OBJECT-TYPE
SYNTAX INTEGER (0..65535)
ACCESS read-only
STATUS optional
DESCRIPTION
        " "
::= { outlet34PDU5 2 }

current34PDU5 OBJECT-TYPE
SYNTAX INTEGER (0..65535)
ACCESS read-only
STATUS optional
DESCRIPTION
        " "
::= { outlet34PDU5 3 }

power34PDU5 OBJECT-TYPE
SYNTAX INTEGER (0..65535)
ACCESS read-only
STATUS optional
DESCRIPTION
        " "
::= { outlet34PDU5 4 }

pf34PDU5 OBJECT-TYPE
SYNTAX INTEGER (0..65535)
ACCESS read-only
STATUS optional
DESCRIPTION
        " "
::= { outlet34PDU5 5 }

energy34PDU5 OBJECT-TYPE
SYNTAX INTEGER (0..65535)
ACCESS read-only
STATUS optional
DESCRIPTION
        " "
::= { outlet34PDU5 6 }

switch35PDU5 OBJECT-TYPE
SYNTAX INTEGER (0..3)
ACCESS read-write
STATUS optional
DESCRIPTION
        " "
::= { outlet35PDU5 1 }

voltage35PDU5 OBJECT-TYPE
SYNTAX INTEGER (0..65535)
ACCESS read-only
STATUS optional
DESCRIPTION
        " "
::= { outlet35PDU5 2 }

current35PDU5 OBJECT-TYPE
SYNTAX INTEGER (0..65535)
ACCESS read-only
STATUS optional
DESCRIPTION
        " "
::= { outlet35PDU5 3 }

power35PDU5 OBJECT-TYPE
SYNTAX INTEGER (0..65535)
ACCESS read-only
STATUS optional
DESCRIPTION
        " "
::= { outlet35PDU5 4 }

pf35PDU5 OBJECT-TYPE
SYNTAX INTEGER (0..65535)
ACCESS read-only
STATUS optional
DESCRIPTION
        " "
::= { outlet35PDU5 5 }

energy35PDU5 OBJECT-TYPE
SYNTAX INTEGER (0..65535)
ACCESS read-only
STATUS optional
DESCRIPTION
        " "
::= { outlet35PDU5 6 }

switch36PDU5 OBJECT-TYPE
SYNTAX INTEGER (0..3)
ACCESS read-write
STATUS optional
DESCRIPTION
        " "
::= { outlet36PDU5 1 }

voltage36PDU5 OBJECT-TYPE
SYNTAX INTEGER (0..65535)
ACCESS read-only
STATUS optional
DESCRIPTION
        " "
::= { outlet36PDU5 2 }

current36PDU5 OBJECT-TYPE
SYNTAX INTEGER (0..65535)
ACCESS read-only
STATUS optional
DESCRIPTION
        " "
::= { outlet36PDU5 3 }

power36PDU5 OBJECT-TYPE
SYNTAX INTEGER (0..65535)
ACCESS read-only
STATUS optional
DESCRIPTION
        " "
::= { outlet36PDU5 4 }

pf36PDU5 OBJECT-TYPE
SYNTAX INTEGER (0..65535)
ACCESS read-only
STATUS optional
DESCRIPTION
        " "
::= { outlet36PDU5 5 }

energy36PDU5 OBJECT-TYPE
SYNTAX INTEGER (0..65535)
ACCESS read-only
STATUS optional
DESCRIPTION
        " "
::= { outlet36PDU5 6 }

sensor1 OBJECT IDENTIFIER ::= { pdu5 4 }

temperature1PDU5 OBJECT-TYPE
SYNTAX INTEGER (0..65535)
ACCESS read-only
STATUS optional
DESCRIPTION
        " "
::= { sensor1 1 }

humidity1PDU5 OBJECT-TYPE
SYNTAX INTEGER (0..65535)
ACCESS read-only
STATUS optional
DESCRIPTION
        " "
::= { sensor1 2 }

temperature2PDU5 OBJECT-TYPE
SYNTAX INTEGER (0..65535)
ACCESS read-only
STATUS optional
DESCRIPTION
        " "
::= { sensor1 3 }

humidity2PDU5 OBJECT-TYPE
SYNTAX INTEGER (0..65535)
ACCESS read-only
STATUS optional
DESCRIPTION
        " "
::= { sensor1 4 }

inputStatus1PDU5 OBJECT-TYPE
SYNTAX INTEGER (0..1)
ACCESS read-only
STATUS optional
DESCRIPTION
        " "
::= { sensor1 5 }

inputStatus2PDU5 OBJECT-TYPE
SYNTAX INTEGER (0..1)
ACCESS read-only
STATUS optional
DESCRIPTION
        " "
::= { sensor1 6 }

inputStatus3PDU5 OBJECT-TYPE
SYNTAX INTEGER (0..1)
ACCESS read-only
STATUS optional
DESCRIPTION
        " "
::= { sensor1 7 }

inputStatus4PDU5 OBJECT-TYPE
SYNTAX INTEGER (0..1)
ACCESS read-only
STATUS optional
DESCRIPTION
        " "
::= { sensor1 8 }

doStatus1PDU5 OBJECT-TYPE
SYNTAX INTEGER (0..1)
ACCESS read-only
STATUS optional
DESCRIPTION
        " "
::= { sensor1 9 }

doStatus2PDU5 OBJECT-TYPE
SYNTAX INTEGER (0..1)
ACCESS read-only
STATUS optional
DESCRIPTION
        " "
::= { sensor1 10 }

baseinfo1 OBJECT IDENTIFIER ::= { pdu6 1 }

cascadeAlarmPDU6 OBJECT-TYPE
SYNTAX INTEGER (0..3)
ACCESS read-only
STATUS optional
DESCRIPTION
        " "
::= { baseinfo1 1 }

deviceNamePDU6 OBJECT-TYPE
SYNTAX DisplayString (SIZE (32))
ACCESS read-write
STATUS optional
DESCRIPTION
        " "
::= { baseinfo1 2 }

outletNumberPDU6 OBJECT-TYPE
SYNTAX INTEGER (0..36)
ACCESS read-only
STATUS optional
DESCRIPTION
        " "
::= { baseinfo1 3 }

temphum1WarnStatPDU6 OBJECT-TYPE
SYNTAX INTEGER (0..127)
ACCESS read-only
STATUS optional
DESCRIPTION
        " "
::= { baseinfo1 4 }

temphum2WarnStatPDU6 OBJECT-TYPE
SYNTAX INTEGER (0..127)
ACCESS read-only
STATUS optional
DESCRIPTION
        " "
::= { baseinfo1 5 }

input1WarnStatPDU6 OBJECT-TYPE
SYNTAX INTEGER (0..1)
ACCESS read-only
STATUS optional
DESCRIPTION
        " "
::= { baseinfo1 6 }

input2WarnStatPDU6 OBJECT-TYPE
SYNTAX INTEGER (0..1)
ACCESS read-only
STATUS optional
DESCRIPTION
        " "
::= { baseinfo1 7 }

input3WarnStatPDU6 OBJECT-TYPE
SYNTAX INTEGER (0..1)
ACCESS read-only
STATUS optional
DESCRIPTION
        " "
::= { baseinfo1 8 }

input4WarnStatPDU6 OBJECT-TYPE
SYNTAX INTEGER (0..1)
ACCESS read-only
STATUS optional
DESCRIPTION
        " "
::= { baseinfo1 9 }

currentL1WarnStatPDU6 OBJECT-TYPE
SYNTAX INTEGER (0..127)
ACCESS read-only
STATUS optional
DESCRIPTION
        " "
::= { baseinfo1 10 }

currentL2WarnStatPDU6 OBJECT-TYPE
SYNTAX INTEGER (0..127)
ACCESS read-only
STATUS optional
DESCRIPTION
        " "
::= { baseinfo1 11 }

currentL3WarnStatPDU6 OBJECT-TYPE
SYNTAX INTEGER (0..127)
ACCESS read-only
STATUS optional
DESCRIPTION
        " "
::= { baseinfo1 12 }

voltageL1WarnStatPDU6 OBJECT-TYPE
SYNTAX INTEGER (0..127)
ACCESS read-only
STATUS optional
DESCRIPTION
        " "
::= { baseinfo1 13 }

voltageL2WarnStatPDU6 OBJECT-TYPE
SYNTAX INTEGER (0..127)
ACCESS read-only
STATUS optional
DESCRIPTION
        " "
::= { baseinfo1 14 }

voltageL3WarnStatPDU6 OBJECT-TYPE
SYNTAX INTEGER (0..127)
ACCESS read-only
STATUS optional
DESCRIPTION
        " "
::= { baseinfo1 15 }

outlet1WarnStatPDU6 OBJECT-TYPE
SYNTAX INTEGER (0..127)
ACCESS read-only
STATUS optional
DESCRIPTION
        " "
::= { baseinfo1 16 }

outlet2WarnStatPDU6 OBJECT-TYPE
SYNTAX INTEGER (0..127)
ACCESS read-only
STATUS optional
DESCRIPTION
        " "
::= { baseinfo1 17 }

outlet3WarnStatPDU6 OBJECT-TYPE
SYNTAX INTEGER (0..127)
ACCESS read-only
STATUS optional
DESCRIPTION
        " "
::= { baseinfo1 18 }

outlet4WarnStatPDU6 OBJECT-TYPE
SYNTAX INTEGER (0..127)
ACCESS read-only
STATUS optional
DESCRIPTION
        " "
::= { baseinfo1 19 }

outlet5WarnStatPDU6 OBJECT-TYPE
SYNTAX INTEGER (0..127)
ACCESS read-only
STATUS optional
DESCRIPTION
        " "
::= { baseinfo1 20 }

outlet6WarnStatPDU6 OBJECT-TYPE
SYNTAX INTEGER (0..127)
ACCESS read-only
STATUS optional
DESCRIPTION
        " "
::= { baseinfo1 21 }

outlet7WarnStatPDU6 OBJECT-TYPE
SYNTAX INTEGER (0..127)
ACCESS read-only
STATUS optional
DESCRIPTION
        " "
::= { baseinfo1 22 }

outlet8WarnStatPDU6 OBJECT-TYPE
SYNTAX INTEGER (0..127)
ACCESS read-only
STATUS optional
DESCRIPTION
        " "
::= { baseinfo1 23 }

outlet9WarnStatPDU6 OBJECT-TYPE
SYNTAX INTEGER (0..127)
ACCESS read-only
STATUS optional
DESCRIPTION
        " "
::= { baseinfo1 24 }

outlet10WarnStatPDU6 OBJECT-TYPE
SYNTAX INTEGER (0..127)
ACCESS read-only
STATUS optional
DESCRIPTION
        " "
::= { baseinfo1 25 }

outlet11WarnStatPDU6 OBJECT-TYPE
SYNTAX INTEGER (0..127)
ACCESS read-only
STATUS optional
DESCRIPTION
        " "
::= { baseinfo1 26 }

outlet12WarnStatPDU6 OBJECT-TYPE
SYNTAX INTEGER (0..127)
ACCESS read-only
STATUS optional
DESCRIPTION
        " "
::= { baseinfo1 27 }

outlet13WarnStatPDU6 OBJECT-TYPE
SYNTAX INTEGER (0..127)
ACCESS read-only
STATUS optional
DESCRIPTION
        " "
::= { baseinfo1 28 }

outlet14WarnStatPDU6 OBJECT-TYPE
SYNTAX INTEGER (0..127)
ACCESS read-only
STATUS optional
DESCRIPTION
        " "
::= { baseinfo1 29 }

outlet15WarnStatPDU6 OBJECT-TYPE
SYNTAX INTEGER (0..127)
ACCESS read-only
STATUS optional
DESCRIPTION
        " "
::= { baseinfo1 30 }

outlet16WarnStatPDU6 OBJECT-TYPE
SYNTAX INTEGER (0..127)
ACCESS read-only
STATUS optional
DESCRIPTION
        " "
::= { baseinfo1 31 }

outlet17WarnStatPDU6 OBJECT-TYPE
SYNTAX INTEGER (0..127)
ACCESS read-only
STATUS optional
DESCRIPTION
        " "
::= { baseinfo1 32 }

outlet18WarnStatPDU6 OBJECT-TYPE
SYNTAX INTEGER (0..127)
ACCESS read-only
STATUS optional
DESCRIPTION
        " "
::= { baseinfo1 33 }

outlet19WarnStatPDU6 OBJECT-TYPE
SYNTAX INTEGER (0..127)
ACCESS read-only
STATUS optional
DESCRIPTION
        " "
::= { baseinfo1 34 }

outlet20WarnStatPDU6 OBJECT-TYPE
SYNTAX INTEGER (0..127)
ACCESS read-only
STATUS optional
DESCRIPTION
        " "
::= { baseinfo1 35 }

outlet21WarnStatPDU6 OBJECT-TYPE
SYNTAX INTEGER (0..127)
ACCESS read-only
STATUS optional
DESCRIPTION
        " "
::= { baseinfo1 36 }

outlet22WarnStatPDU6 OBJECT-TYPE
SYNTAX INTEGER (0..127)
ACCESS read-only
STATUS optional
DESCRIPTION
        " "
::= { baseinfo1 37 }

outlet23WarnStatPDU6 OBJECT-TYPE
SYNTAX INTEGER (0..127)
ACCESS read-only
STATUS optional
DESCRIPTION
        " "
::= { baseinfo1 38 }

outlet24WarnStatPDU6 OBJECT-TYPE
SYNTAX INTEGER (0..127)
ACCESS read-only
STATUS optional
DESCRIPTION
        " "
::= { baseinfo1 39 }

outlet25WarnStatPDU6 OBJECT-TYPE
SYNTAX INTEGER (0..127)
ACCESS read-only
STATUS optional
DESCRIPTION
        " "
::= { baseinfo1 40 }

outlet26WarnStatPDU6 OBJECT-TYPE
SYNTAX INTEGER (0..127)
ACCESS read-only
STATUS optional
DESCRIPTION
        " "
::= { baseinfo1 41 }

outlet27WarnStatPDU6 OBJECT-TYPE
SYNTAX INTEGER (0..127)
ACCESS read-only
STATUS optional
DESCRIPTION
        " "
::= { baseinfo1 42 }

outlet28WarnStatPDU6 OBJECT-TYPE
SYNTAX INTEGER (0..127)
ACCESS read-only
STATUS optional
DESCRIPTION
        " "
::= { baseinfo1 43 }

outlet29WarnStatPDU6 OBJECT-TYPE
SYNTAX INTEGER (0..127)
ACCESS read-only
STATUS optional
DESCRIPTION
        " "
::= { baseinfo1 44 }

outlet30WarnStatPDU6 OBJECT-TYPE
SYNTAX INTEGER (0..127)
ACCESS read-only
STATUS optional
DESCRIPTION
        " "
::= { baseinfo1 45 }

outlet31WarnStatPDU6 OBJECT-TYPE
SYNTAX INTEGER (0..127)
ACCESS read-only
STATUS optional
DESCRIPTION
        " "
::= { baseinfo1 46 }

outlet32WarnStatPDU6 OBJECT-TYPE
SYNTAX INTEGER (0..127)
ACCESS read-only
STATUS optional
DESCRIPTION
        " "
::= { baseinfo1 47 }

outlet33WarnStatPDU6 OBJECT-TYPE
SYNTAX INTEGER (0..127)
ACCESS read-only
STATUS optional
DESCRIPTION
        " "
::= { baseinfo1 48 }

outlet34WarnStatPDU6 OBJECT-TYPE
SYNTAX INTEGER (0..127)
ACCESS read-only
STATUS optional
DESCRIPTION
        " "
::= { baseinfo1 49 }

outlet35WarnStatPDU6 OBJECT-TYPE
SYNTAX INTEGER (0..127)
ACCESS read-only
STATUS optional
DESCRIPTION
        " "
::= { baseinfo1 50 }

outlet36WarnStatPDU6 OBJECT-TYPE
SYNTAX INTEGER (0..127)
ACCESS read-only
STATUS optional
DESCRIPTION
        " "
::= { baseinfo1 51 }

input1 OBJECT IDENTIFIER ::= { pdu6 2 }

currentL1PDU6 OBJECT-TYPE
SYNTAX INTEGER (0..65535)
ACCESS read-only
STATUS optional
DESCRIPTION
        " "
::= { input1 1 }

voltageL1PDU6 OBJECT-TYPE
SYNTAX INTEGER (0..65535)
ACCESS read-only
STATUS optional
DESCRIPTION
        " "
::= { input1 2 }

powerL1PDU6 OBJECT-TYPE
SYNTAX INTEGER (0..65535)
ACCESS read-only
STATUS optional
DESCRIPTION
        " "
::= { input1 3 }

pfL1PDU6 OBJECT-TYPE
SYNTAX INTEGER (0..65535)
ACCESS read-only
STATUS optional
DESCRIPTION
        " "
::= { input1 4 }

energyL1PDU6 OBJECT-TYPE
SYNTAX INTEGER (0..65535)
ACCESS read-only
STATUS optional
DESCRIPTION
        " "
::= { input1 5 }

currentL2PDU6 OBJECT-TYPE
SYNTAX INTEGER (0..65535)
ACCESS read-only
STATUS optional
DESCRIPTION
        " "
::= { input1 6 }

voltageL2PDU6 OBJECT-TYPE
SYNTAX INTEGER (0..65535)
ACCESS read-only
STATUS optional
DESCRIPTION
        " "
::= { input1 7 }

powerL2PDU6 OBJECT-TYPE
SYNTAX INTEGER (0..65535)
ACCESS read-only
STATUS optional
DESCRIPTION
        " "
::= { input1 8 }

pfL2PDU6 OBJECT-TYPE
SYNTAX INTEGER (0..65535)
ACCESS read-only
STATUS optional
DESCRIPTION
        " "
::= { input1 9 }

energyL2PDU6 OBJECT-TYPE
SYNTAX INTEGER (0..65535)
ACCESS read-only
STATUS optional
DESCRIPTION
        " "
::= { input1 10 }

currentL3PDU6 OBJECT-TYPE
SYNTAX INTEGER (0..65535)
ACCESS read-only
STATUS optional
DESCRIPTION
        " "
::= { input1 11 }

voltageL3PDU6 OBJECT-TYPE
SYNTAX INTEGER (0..65535)
ACCESS read-only
STATUS optional
DESCRIPTION
        " "
::= { input1 12 }

powerL3PDU6 OBJECT-TYPE
SYNTAX INTEGER (0..65535)
ACCESS read-only
STATUS optional
DESCRIPTION
        " "
::= { input1 13 }

pfL3PDU6 OBJECT-TYPE
SYNTAX INTEGER (0..65535)
ACCESS read-only
STATUS optional
DESCRIPTION
        " "
::= { input1 14 }

energyL3PDU6 OBJECT-TYPE
SYNTAX INTEGER (0..65535)
ACCESS read-only
STATUS optional
DESCRIPTION
        " "
::= { input1 15 }

outletinfo1 OBJECT IDENTIFIER ::= { pdu6 3 }

outlet1PDU6 OBJECT IDENTIFIER ::= { outletinfo1 1 }

outlet2PDU6 OBJECT IDENTIFIER ::= { outletinfo1 2 }

outlet3PDU6 OBJECT IDENTIFIER ::= { outletinfo1 3 }

outlet4PDU6 OBJECT IDENTIFIER ::= { outletinfo1 4 }

outlet5PDU6 OBJECT IDENTIFIER ::= { outletinfo1 5 }

outlet6PDU6 OBJECT IDENTIFIER ::= { outletinfo1 6 }

outlet7PDU6 OBJECT IDENTIFIER ::= { outletinfo1 7 }

outlet8PDU6 OBJECT IDENTIFIER ::= { outletinfo1 8 }

outlet9PDU6 OBJECT IDENTIFIER ::= { outletinfo1 9 }

outlet10PDU6 OBJECT IDENTIFIER ::= { outletinfo1 10 }

outlet11PDU6 OBJECT IDENTIFIER ::= { outletinfo1 11 }

outlet12PDU6 OBJECT IDENTIFIER ::= { outletinfo1 12 }

outlet13PDU6 OBJECT IDENTIFIER ::= { outletinfo1 13 }

outlet14PDU6 OBJECT IDENTIFIER ::= { outletinfo1 14 }

outlet15PDU6 OBJECT IDENTIFIER ::= { outletinfo1 15 }

outlet16PDU6 OBJECT IDENTIFIER ::= { outletinfo1 16 }

outlet17PDU6 OBJECT IDENTIFIER ::= { outletinfo1 17 }

outlet18PDU6 OBJECT IDENTIFIER ::= { outletinfo1 18 }

outlet19PDU6 OBJECT IDENTIFIER ::= { outletinfo1 19 }

outlet20PDU6 OBJECT IDENTIFIER ::= { outletinfo1 20 }

outlet21PDU6 OBJECT IDENTIFIER ::= { outletinfo1 21 }

outlet22PDU6 OBJECT IDENTIFIER ::= { outletinfo1 22 }

outlet23PDU6 OBJECT IDENTIFIER ::= { outletinfo1 23 }

outlet24PDU6 OBJECT IDENTIFIER ::= { outletinfo1 24 }

outlet25PDU6 OBJECT IDENTIFIER ::= { outletinfo1 25 }

outlet26PDU6 OBJECT IDENTIFIER ::= { outletinfo1 26 }

outlet27PDU6 OBJECT IDENTIFIER ::= { outletinfo1 27 }

outlet28PDU6 OBJECT IDENTIFIER ::= { outletinfo1 28 }

outlet29PDU6 OBJECT IDENTIFIER ::= { outletinfo1 29 }

outlet30PDU6 OBJECT IDENTIFIER ::= { outletinfo1 30 }

outlet31PDU6 OBJECT IDENTIFIER ::= { outletinfo1 31 }

outlet32PDU6 OBJECT IDENTIFIER ::= { outletinfo1 32 }

outlet33PDU6 OBJECT IDENTIFIER ::= { outletinfo1 33 }

outlet34PDU6 OBJECT IDENTIFIER ::= { outletinfo1 34 }

outlet35PDU6 OBJECT IDENTIFIER ::= { outletinfo1 35 }

outlet36PDU6 OBJECT IDENTIFIER ::= { outletinfo1 36 }

switch1PDU6 OBJECT-TYPE
SYNTAX INTEGER (0..3)
ACCESS read-write
STATUS optional
DESCRIPTION
        " "
::= { outlet1PDU6 1 }

voltage1PDU6 OBJECT-TYPE
SYNTAX INTEGER (0..65535)
ACCESS read-only
STATUS optional
DESCRIPTION
        " "
::= { outlet1PDU6 2 }

current1PDU6 OBJECT-TYPE
SYNTAX INTEGER (0..65535)
ACCESS read-only
STATUS optional
DESCRIPTION
        " "
::= { outlet1PDU6 3 }

power1PDU6 OBJECT-TYPE
SYNTAX INTEGER (0..65535)
ACCESS read-only
STATUS optional
DESCRIPTION
        " "
::= { outlet1PDU6 4 }

pf1PDU6 OBJECT-TYPE
SYNTAX INTEGER (0..65535)
ACCESS read-only
STATUS optional
DESCRIPTION
        " "
::= { outlet1PDU6 5 }

energy1PDU6 OBJECT-TYPE
SYNTAX INTEGER (0..65535)
ACCESS read-only
STATUS optional
DESCRIPTION
        " "
::= { outlet1PDU6 6 }

switch2PDU6 OBJECT-TYPE
SYNTAX INTEGER (0..3)
ACCESS read-write
STATUS optional
DESCRIPTION
        " "
::= { outlet2PDU6 1 }

voltage2PDU6 OBJECT-TYPE
SYNTAX INTEGER (0..65535)
ACCESS read-only
STATUS optional
DESCRIPTION
        " "
::= { outlet2PDU6 2 }

current2PDU6 OBJECT-TYPE
SYNTAX INTEGER (0..65535)
ACCESS read-only
STATUS optional
DESCRIPTION
        " "
::= { outlet2PDU6 3 }

power2PDU6 OBJECT-TYPE
SYNTAX INTEGER (0..65535)
ACCESS read-only
STATUS optional
DESCRIPTION
        " "
::= { outlet2PDU6 4 }

pf2PDU6 OBJECT-TYPE
SYNTAX INTEGER (0..65535)
ACCESS read-only
STATUS optional
DESCRIPTION
        " "
::= { outlet2PDU6 5 }

energy2PDU6 OBJECT-TYPE
SYNTAX INTEGER (0..65535)
ACCESS read-only
STATUS optional
DESCRIPTION
        " "
::= { outlet2PDU6 6 }

switch3PDU6 OBJECT-TYPE
SYNTAX INTEGER (0..3)
ACCESS read-write
STATUS optional
DESCRIPTION
        " "
::= { outlet3PDU6 1 }

voltage3PDU6 OBJECT-TYPE
SYNTAX INTEGER (0..65535)
ACCESS read-only
STATUS optional
DESCRIPTION
        " "
::= { outlet3PDU6 2 }

current3PDU6 OBJECT-TYPE
SYNTAX INTEGER (0..65535)
ACCESS read-only
STATUS optional
DESCRIPTION
        " "
::= { outlet3PDU6 3 }

power3PDU6 OBJECT-TYPE
SYNTAX INTEGER (0..65535)
ACCESS read-only
STATUS optional
DESCRIPTION
        " "
::= { outlet3PDU6 4 }

pf3PDU6 OBJECT-TYPE
SYNTAX INTEGER (0..65535)
ACCESS read-only
STATUS optional
DESCRIPTION
        " "
::= { outlet3PDU6 5 }

energy3PDU6 OBJECT-TYPE
SYNTAX INTEGER (0..65535)
ACCESS read-only
STATUS optional
DESCRIPTION
        " "
::= { outlet3PDU6 6 }

switch4PDU6 OBJECT-TYPE
SYNTAX INTEGER (0..3)
ACCESS read-write
STATUS optional
DESCRIPTION
        " "
::= { outlet4PDU6 1 }

voltage4PDU6 OBJECT-TYPE
SYNTAX INTEGER (0..65535)
ACCESS read-only
STATUS optional
DESCRIPTION
        " "
::= { outlet4PDU6 2 }

current4PDU6 OBJECT-TYPE
SYNTAX INTEGER (0..65535)
ACCESS read-only
STATUS optional
DESCRIPTION
        " "
::= { outlet4PDU6 3 }

power4PDU6 OBJECT-TYPE
SYNTAX INTEGER (0..65535)
ACCESS read-only
STATUS optional
DESCRIPTION
        " "
::= { outlet4PDU6 4 }

pf4PDU6 OBJECT-TYPE
SYNTAX INTEGER (0..65535)
ACCESS read-only
STATUS optional
DESCRIPTION
        " "
::= { outlet4PDU6 5 }

energy4PDU6 OBJECT-TYPE
SYNTAX INTEGER (0..65535)
ACCESS read-only
STATUS optional
DESCRIPTION
        " "
::= { outlet4PDU6 6 }

switch5PDU6 OBJECT-TYPE
SYNTAX INTEGER (0..3)
ACCESS read-write
STATUS optional
DESCRIPTION
        " "
::= { outlet5PDU6 1 }

voltage5PDU6 OBJECT-TYPE
SYNTAX INTEGER (0..65535)
ACCESS read-only
STATUS optional
DESCRIPTION
        " "
::= { outlet5PDU6 2 }

current5PDU6 OBJECT-TYPE
SYNTAX INTEGER (0..65535)
ACCESS read-only
STATUS optional
DESCRIPTION
        " "
::= { outlet5PDU6 3 }

power5PDU6 OBJECT-TYPE
SYNTAX INTEGER (0..65535)
ACCESS read-only
STATUS optional
DESCRIPTION
        " "
::= { outlet5PDU6 4 }

pf5PDU6 OBJECT-TYPE
SYNTAX INTEGER (0..65535)
ACCESS read-only
STATUS optional
DESCRIPTION
        " "
::= { outlet5PDU6 5 }

energy5PDU6 OBJECT-TYPE
SYNTAX INTEGER (0..65535)
ACCESS read-only
STATUS optional
DESCRIPTION
        " "
::= { outlet5PDU6 6 }

switch6PDU6 OBJECT-TYPE
SYNTAX INTEGER (0..3)
ACCESS read-write
STATUS optional
DESCRIPTION
        " "
::= { outlet6PDU6 1 }

voltage6PDU6 OBJECT-TYPE
SYNTAX INTEGER (0..65535)
ACCESS read-only
STATUS optional
DESCRIPTION
        " "
::= { outlet6PDU6 2 }

current6PDU6 OBJECT-TYPE
SYNTAX INTEGER (0..65535)
ACCESS read-only
STATUS optional
DESCRIPTION
        " "
::= { outlet6PDU6 3 }

power6PDU6 OBJECT-TYPE
SYNTAX INTEGER (0..65535)
ACCESS read-only
STATUS optional
DESCRIPTION
        " "
::= { outlet6PDU6 4 }

pf6PDU6 OBJECT-TYPE
SYNTAX INTEGER (0..65535)
ACCESS read-only
STATUS optional
DESCRIPTION
        " "
::= { outlet6PDU6 5 }

energy6PDU6 OBJECT-TYPE
SYNTAX INTEGER (0..65535)
ACCESS read-only
STATUS optional
DESCRIPTION
        " "
::= { outlet6PDU6 6 }

switch7PDU6 OBJECT-TYPE
SYNTAX INTEGER (0..3)
ACCESS read-write
STATUS optional
DESCRIPTION
        " "
::= { outlet7PDU6 1 }

voltage7PDU6 OBJECT-TYPE
SYNTAX INTEGER (0..65535)
ACCESS read-only
STATUS optional
DESCRIPTION
        " "
::= { outlet7PDU6 2 }

current7PDU6 OBJECT-TYPE
SYNTAX INTEGER (0..65535)
ACCESS read-only
STATUS optional
DESCRIPTION
        " "
::= { outlet7PDU6 3 }

power7PDU6 OBJECT-TYPE
SYNTAX INTEGER (0..65535)
ACCESS read-only
STATUS optional
DESCRIPTION
        " "
::= { outlet7PDU6 4 }

pf7PDU6 OBJECT-TYPE
SYNTAX INTEGER (0..65535)
ACCESS read-only
STATUS optional
DESCRIPTION
        " "
::= { outlet7PDU6 5 }

energy7PDU6 OBJECT-TYPE
SYNTAX INTEGER (0..65535)
ACCESS read-only
STATUS optional
DESCRIPTION
        " "
::= { outlet7PDU6 6 }

switch8PDU6 OBJECT-TYPE
SYNTAX INTEGER (0..3)
ACCESS read-write
STATUS optional
DESCRIPTION
        " "
::= { outlet8PDU6 1 }

voltage8PDU6 OBJECT-TYPE
SYNTAX INTEGER (0..65535)
ACCESS read-only
STATUS optional
DESCRIPTION
        " "
::= { outlet8PDU6 2 }

current8PDU6 OBJECT-TYPE
SYNTAX INTEGER (0..65535)
ACCESS read-only
STATUS optional
DESCRIPTION
        " "
::= { outlet8PDU6 3 }

power8PDU6 OBJECT-TYPE
SYNTAX INTEGER (0..65535)
ACCESS read-only
STATUS optional
DESCRIPTION
        " "
::= { outlet8PDU6 4 }

pf8PDU6 OBJECT-TYPE
SYNTAX INTEGER (0..65535)
ACCESS read-only
STATUS optional
DESCRIPTION
        " "
::= { outlet8PDU6 5 }

energy8PDU6 OBJECT-TYPE
SYNTAX INTEGER (0..65535)
ACCESS read-only
STATUS optional
DESCRIPTION
        " "
::= { outlet8PDU6 6 }

switch9PDU6 OBJECT-TYPE
SYNTAX INTEGER (0..3)
ACCESS read-write
STATUS optional
DESCRIPTION
        " "
::= { outlet9PDU6 1 }

voltage9PDU6 OBJECT-TYPE
SYNTAX INTEGER (0..65535)
ACCESS read-only
STATUS optional
DESCRIPTION
        " "
::= { outlet9PDU6 2 }

current9PDU6 OBJECT-TYPE
SYNTAX INTEGER (0..65535)
ACCESS read-only
STATUS optional
DESCRIPTION
        " "
::= { outlet9PDU6 3 }

power9PDU6 OBJECT-TYPE
SYNTAX INTEGER (0..65535)
ACCESS read-only
STATUS optional
DESCRIPTION
        " "
::= { outlet9PDU6 4 }

pf9PDU6 OBJECT-TYPE
SYNTAX INTEGER (0..65535)
ACCESS read-only
STATUS optional
DESCRIPTION
        " "
::= { outlet9PDU6 5 }

energy9PDU6 OBJECT-TYPE
SYNTAX INTEGER (0..65535)
ACCESS read-only
STATUS optional
DESCRIPTION
        " "
::= { outlet9PDU6 6 }

switch10PDU6 OBJECT-TYPE
SYNTAX INTEGER (0..3)
ACCESS read-write
STATUS optional
DESCRIPTION
        " "
::= { outlet10PDU6 1 }

voltage10PDU6 OBJECT-TYPE
SYNTAX INTEGER (0..65535)
ACCESS read-only
STATUS optional
DESCRIPTION
        " "
::= { outlet10PDU6 2 }

current10PDU6 OBJECT-TYPE
SYNTAX INTEGER (0..65535)
ACCESS read-only
STATUS optional
DESCRIPTION
        " "
::= { outlet10PDU6 3 }

power10PDU6 OBJECT-TYPE
SYNTAX INTEGER (0..65535)
ACCESS read-only
STATUS optional
DESCRIPTION
        " "
::= { outlet10PDU6 4 }

pf10PDU6 OBJECT-TYPE
SYNTAX INTEGER (0..65535)
ACCESS read-only
STATUS optional
DESCRIPTION
        " "
::= { outlet10PDU6 5 }

energy10PDU6 OBJECT-TYPE
SYNTAX INTEGER (0..65535)
ACCESS read-only
STATUS optional
DESCRIPTION
        " "
::= { outlet10PDU6 6 }

switch11PDU6 OBJECT-TYPE
SYNTAX INTEGER (0..3)
ACCESS read-write
STATUS optional
DESCRIPTION
        " "
::= { outlet11PDU6 1 }

voltage11PDU6 OBJECT-TYPE
SYNTAX INTEGER (0..65535)
ACCESS read-only
STATUS optional
DESCRIPTION
        " "
::= { outlet11PDU6 2 }

current11PDU6 OBJECT-TYPE
SYNTAX INTEGER (0..65535)
ACCESS read-only
STATUS optional
DESCRIPTION
        " "
::= { outlet11PDU6 3 }

power11PDU6 OBJECT-TYPE
SYNTAX INTEGER (0..65535)
ACCESS read-only
STATUS optional
DESCRIPTION
        " "
::= { outlet11PDU6 4 }

pf11PDU6 OBJECT-TYPE
SYNTAX INTEGER (0..65535)
ACCESS read-only
STATUS optional
DESCRIPTION
        " "
::= { outlet11PDU6 5 }

energy11PDU6 OBJECT-TYPE
SYNTAX INTEGER (0..65535)
ACCESS read-only
STATUS optional
DESCRIPTION
        " "
::= { outlet11PDU6 6 }

switch12PDU6 OBJECT-TYPE
SYNTAX INTEGER (0..3)
ACCESS read-write
STATUS optional
DESCRIPTION
        " "
::= { outlet12PDU6 1 }

voltage12PDU6 OBJECT-TYPE
SYNTAX INTEGER (0..65535)
ACCESS read-only
STATUS optional
DESCRIPTION
        " "
::= { outlet12PDU6 2 }

current12PDU6 OBJECT-TYPE
SYNTAX INTEGER (0..65535)
ACCESS read-only
STATUS optional
DESCRIPTION
        " "
::= { outlet12PDU6 3 }

power12PDU6 OBJECT-TYPE
SYNTAX INTEGER (0..65535)
ACCESS read-only
STATUS optional
DESCRIPTION
        " "
::= { outlet12PDU6 4 }

pf12PDU6 OBJECT-TYPE
SYNTAX INTEGER (0..65535)
ACCESS read-only
STATUS optional
DESCRIPTION
        " "
::= { outlet12PDU6 5 }

energy12PDU6 OBJECT-TYPE
SYNTAX INTEGER (0..65535)
ACCESS read-only
STATUS optional
DESCRIPTION
        " "
::= { outlet12PDU6 6 }

switch13PDU6 OBJECT-TYPE
SYNTAX INTEGER (0..3)
ACCESS read-write
STATUS optional
DESCRIPTION
        " "
::= { outlet13PDU6 1 }

voltage13PDU6 OBJECT-TYPE
SYNTAX INTEGER (0..65535)
ACCESS read-only
STATUS optional
DESCRIPTION
        " "
::= { outlet13PDU6 2 }

current13PDU6 OBJECT-TYPE
SYNTAX INTEGER (0..65535)
ACCESS read-only
STATUS optional
DESCRIPTION
        " "
::= { outlet13PDU6 3 }

power13PDU6 OBJECT-TYPE
SYNTAX INTEGER (0..65535)
ACCESS read-only
STATUS optional
DESCRIPTION
        " "
::= { outlet13PDU6 4 }

pf13PDU6 OBJECT-TYPE
SYNTAX INTEGER (0..65535)
ACCESS read-only
STATUS optional
DESCRIPTION
        " "
::= { outlet13PDU6 5 }

energy13PDU6 OBJECT-TYPE
SYNTAX INTEGER (0..65535)
ACCESS read-only
STATUS optional
DESCRIPTION
        " "
::= { outlet13PDU6 6 }

switch14PDU6 OBJECT-TYPE
SYNTAX INTEGER (0..3)
ACCESS read-write
STATUS optional
DESCRIPTION
        " "
::= { outlet14PDU6 1 }

voltage14PDU6 OBJECT-TYPE
SYNTAX INTEGER (0..65535)
ACCESS read-only
STATUS optional
DESCRIPTION
        " "
::= { outlet14PDU6 2 }

current14PDU6 OBJECT-TYPE
SYNTAX INTEGER (0..65535)
ACCESS read-only
STATUS optional
DESCRIPTION
        " "
::= { outlet14PDU6 3 }

power14PDU6 OBJECT-TYPE
SYNTAX INTEGER (0..65535)
ACCESS read-only
STATUS optional
DESCRIPTION
        " "
::= { outlet14PDU6 4 }

pf14PDU6 OBJECT-TYPE
SYNTAX INTEGER (0..65535)
ACCESS read-only
STATUS optional
DESCRIPTION
        " "
::= { outlet14PDU6 5 }

energy14PDU6 OBJECT-TYPE
SYNTAX INTEGER (0..65535)
ACCESS read-only
STATUS optional
DESCRIPTION
        " "
::= { outlet14PDU6 6 }

switch15PDU6 OBJECT-TYPE
SYNTAX INTEGER (0..3)
ACCESS read-write
STATUS optional
DESCRIPTION
        " "
::= { outlet15PDU6 1 }

voltage15PDU6 OBJECT-TYPE
SYNTAX INTEGER (0..65535)
ACCESS read-only
STATUS optional
DESCRIPTION
        " "
::= { outlet15PDU6 2 }

current15PDU6 OBJECT-TYPE
SYNTAX INTEGER (0..65535)
ACCESS read-only
STATUS optional
DESCRIPTION
        " "
::= { outlet15PDU6 3 }

power15PDU6 OBJECT-TYPE
SYNTAX INTEGER (0..65535)
ACCESS read-only
STATUS optional
DESCRIPTION
        " "
::= { outlet15PDU6 4 }

pf15PDU6 OBJECT-TYPE
SYNTAX INTEGER (0..65535)
ACCESS read-only
STATUS optional
DESCRIPTION
        " "
::= { outlet15PDU6 5 }

energy15PDU6 OBJECT-TYPE
SYNTAX INTEGER (0..65535)
ACCESS read-only
STATUS optional
DESCRIPTION
        " "
::= { outlet15PDU6 6 }

switch16PDU6 OBJECT-TYPE
SYNTAX INTEGER (0..3)
ACCESS read-write
STATUS optional
DESCRIPTION
        " "
::= { outlet16PDU6 1 }

voltage16PDU6 OBJECT-TYPE
SYNTAX INTEGER (0..65535)
ACCESS read-only
STATUS optional
DESCRIPTION
        " "
::= { outlet16PDU6 2 }

current16PDU6 OBJECT-TYPE
SYNTAX INTEGER (0..65535)
ACCESS read-only
STATUS optional
DESCRIPTION
        " "
::= { outlet16PDU6 3 }

power16PDU6 OBJECT-TYPE
SYNTAX INTEGER (0..65535)
ACCESS read-only
STATUS optional
DESCRIPTION
        " "
::= { outlet16PDU6 4 }

pf16PDU6 OBJECT-TYPE
SYNTAX INTEGER (0..65535)
ACCESS read-only
STATUS optional
DESCRIPTION
        " "
::= { outlet16PDU6 5 }

energy16PDU6 OBJECT-TYPE
SYNTAX INTEGER (0..65535)
ACCESS read-only
STATUS optional
DESCRIPTION
        " "
::= { outlet16PDU6 6 }

switch17PDU6 OBJECT-TYPE
SYNTAX INTEGER (0..3)
ACCESS read-write
STATUS optional
DESCRIPTION
        " "
::= { outlet17PDU6 1 }

voltage17PDU6 OBJECT-TYPE
SYNTAX INTEGER (0..65535)
ACCESS read-only
STATUS optional
DESCRIPTION
        " "
::= { outlet17PDU6 2 }

current17PDU6 OBJECT-TYPE
SYNTAX INTEGER (0..65535)
ACCESS read-only
STATUS optional
DESCRIPTION
        " "
::= { outlet17PDU6 3 }

power17PDU6 OBJECT-TYPE
SYNTAX INTEGER (0..65535)
ACCESS read-only
STATUS optional
DESCRIPTION
        " "
::= { outlet17PDU6 4 }

pf17PDU6 OBJECT-TYPE
SYNTAX INTEGER (0..65535)
ACCESS read-only
STATUS optional
DESCRIPTION
        " "
::= { outlet17PDU6 5 }

energy17PDU6 OBJECT-TYPE
SYNTAX INTEGER (0..65535)
ACCESS read-only
STATUS optional
DESCRIPTION
        " "
::= { outlet17PDU6 6 }

switch18PDU6 OBJECT-TYPE
SYNTAX INTEGER (0..3)
ACCESS read-write
STATUS optional
DESCRIPTION
        " "
::= { outlet18PDU6 1 }

voltage18PDU6 OBJECT-TYPE
SYNTAX INTEGER (0..65535)
ACCESS read-only
STATUS optional
DESCRIPTION
        " "
::= { outlet18PDU6 2 }

current18PDU6 OBJECT-TYPE
SYNTAX INTEGER (0..65535)
ACCESS read-only
STATUS optional
DESCRIPTION
        " "
::= { outlet18PDU6 3 }

power18PDU6 OBJECT-TYPE
SYNTAX INTEGER (0..65535)
ACCESS read-only
STATUS optional
DESCRIPTION
        " "
::= { outlet18PDU6 4 }

pf18PDU6 OBJECT-TYPE
SYNTAX INTEGER (0..65535)
ACCESS read-only
STATUS optional
DESCRIPTION
        " "
::= { outlet18PDU6 5 }

energy18PDU6 OBJECT-TYPE
SYNTAX INTEGER (0..65535)
ACCESS read-only
STATUS optional
DESCRIPTION
        " "
::= { outlet18PDU6 6 }

switch19PDU6 OBJECT-TYPE
SYNTAX INTEGER (0..3)
ACCESS read-write
STATUS optional
DESCRIPTION
        " "
::= { outlet19PDU6 1 }

voltage19PDU6 OBJECT-TYPE
SYNTAX INTEGER (0..65535)
ACCESS read-only
STATUS optional
DESCRIPTION
        " "
::= { outlet19PDU6 2 }

current19PDU6 OBJECT-TYPE
SYNTAX INTEGER (0..65535)
ACCESS read-only
STATUS optional
DESCRIPTION
        " "
::= { outlet19PDU6 3 }

power19PDU6 OBJECT-TYPE
SYNTAX INTEGER (0..65535)
ACCESS read-only
STATUS optional
DESCRIPTION
        " "
::= { outlet19PDU6 4 }

pf19PDU6 OBJECT-TYPE
SYNTAX INTEGER (0..65535)
ACCESS read-only
STATUS optional
DESCRIPTION
        " "
::= { outlet19PDU6 5 }

energy19PDU6 OBJECT-TYPE
SYNTAX INTEGER (0..65535)
ACCESS read-only
STATUS optional
DESCRIPTION
        " "
::= { outlet19PDU6 6 }

switch20PDU6 OBJECT-TYPE
SYNTAX INTEGER (0..3)
ACCESS read-write
STATUS optional
DESCRIPTION
        " "
::= { outlet20PDU6 1 }

voltage20PDU6 OBJECT-TYPE
SYNTAX INTEGER (0..65535)
ACCESS read-only
STATUS optional
DESCRIPTION
        " "
::= { outlet20PDU6 2 }

current20PDU6 OBJECT-TYPE
SYNTAX INTEGER (0..65535)
ACCESS read-only
STATUS optional
DESCRIPTION
        " "
::= { outlet20PDU6 3 }

power20PDU6 OBJECT-TYPE
SYNTAX INTEGER (0..65535)
ACCESS read-only
STATUS optional
DESCRIPTION
        " "
::= { outlet20PDU6 4 }

pf20PDU6 OBJECT-TYPE
SYNTAX INTEGER (0..65535)
ACCESS read-only
STATUS optional
DESCRIPTION
        " "
::= { outlet20PDU6 5 }

energy20PDU6 OBJECT-TYPE
SYNTAX INTEGER (0..65535)
ACCESS read-only
STATUS optional
DESCRIPTION
        " "
::= { outlet20PDU6 6 }

switch21PDU6 OBJECT-TYPE
SYNTAX INTEGER (0..3)
ACCESS read-write
STATUS optional
DESCRIPTION
        " "
::= { outlet21PDU6 1 }

voltage21PDU6 OBJECT-TYPE
SYNTAX INTEGER (0..65535)
ACCESS read-only
STATUS optional
DESCRIPTION
        " "
::= { outlet21PDU6 2 }

current21PDU6 OBJECT-TYPE
SYNTAX INTEGER (0..65535)
ACCESS read-only
STATUS optional
DESCRIPTION
        " "
::= { outlet21PDU6 3 }

power21PDU6 OBJECT-TYPE
SYNTAX INTEGER (0..65535)
ACCESS read-only
STATUS optional
DESCRIPTION
        " "
::= { outlet21PDU6 4 }

pf21PDU6 OBJECT-TYPE
SYNTAX INTEGER (0..65535)
ACCESS read-only
STATUS optional
DESCRIPTION
        " "
::= { outlet21PDU6 5 }

energy21PDU6 OBJECT-TYPE
SYNTAX INTEGER (0..65535)
ACCESS read-only
STATUS optional
DESCRIPTION
        " "
::= { outlet21PDU6 6 }

switch22PDU6 OBJECT-TYPE
SYNTAX INTEGER (0..3)
ACCESS read-write
STATUS optional
DESCRIPTION
        " "
::= { outlet22PDU6 1 }

voltage22PDU6 OBJECT-TYPE
SYNTAX INTEGER (0..65535)
ACCESS read-only
STATUS optional
DESCRIPTION
        " "
::= { outlet22PDU6 2 }

current22PDU6 OBJECT-TYPE
SYNTAX INTEGER (0..65535)
ACCESS read-only
STATUS optional
DESCRIPTION
        " "
::= { outlet22PDU6 3 }

power22PDU6 OBJECT-TYPE
SYNTAX INTEGER (0..65535)
ACCESS read-only
STATUS optional
DESCRIPTION
        " "
::= { outlet22PDU6 4 }

pf22PDU6 OBJECT-TYPE
SYNTAX INTEGER (0..65535)
ACCESS read-only
STATUS optional
DESCRIPTION
        " "
::= { outlet22PDU6 5 }

energy22PDU6 OBJECT-TYPE
SYNTAX INTEGER (0..65535)
ACCESS read-only
STATUS optional
DESCRIPTION
        " "
::= { outlet22PDU6 6 }

switch23PDU6 OBJECT-TYPE
SYNTAX INTEGER (0..3)
ACCESS read-write
STATUS optional
DESCRIPTION
        " "
::= { outlet23PDU6 1 }

voltage23PDU6 OBJECT-TYPE
SYNTAX INTEGER (0..65535)
ACCESS read-only
STATUS optional
DESCRIPTION
        " "
::= { outlet23PDU6 2 }

current23PDU6 OBJECT-TYPE
SYNTAX INTEGER (0..65535)
ACCESS read-only
STATUS optional
DESCRIPTION
        " "
::= { outlet23PDU6 3 }

power23PDU6 OBJECT-TYPE
SYNTAX INTEGER (0..65535)
ACCESS read-only
STATUS optional
DESCRIPTION
        " "
::= { outlet23PDU6 4 }

pf23PDU6 OBJECT-TYPE
SYNTAX INTEGER (0..65535)
ACCESS read-only
STATUS optional
DESCRIPTION
        " "
::= { outlet23PDU6 5 }

energy23PDU6 OBJECT-TYPE
SYNTAX INTEGER (0..65535)
ACCESS read-only
STATUS optional
DESCRIPTION
        " "
::= { outlet23PDU6 6 }

switch24PDU6 OBJECT-TYPE
SYNTAX INTEGER (0..3)
ACCESS read-write
STATUS optional
DESCRIPTION
        " "
::= { outlet24PDU6 1 }

voltage24PDU6 OBJECT-TYPE
SYNTAX INTEGER (0..65535)
ACCESS read-only
STATUS optional
DESCRIPTION
        " "
::= { outlet24PDU6 2 }

current24PDU6 OBJECT-TYPE
SYNTAX INTEGER (0..65535)
ACCESS read-only
STATUS optional
DESCRIPTION
        " "
::= { outlet24PDU6 3 }

power24PDU6 OBJECT-TYPE
SYNTAX INTEGER (0..65535)
ACCESS read-only
STATUS optional
DESCRIPTION
        " "
::= { outlet24PDU6 4 }

pf24PDU6 OBJECT-TYPE
SYNTAX INTEGER (0..65535)
ACCESS read-only
STATUS optional
DESCRIPTION
        " "
::= { outlet24PDU6 5 }

energy24PDU6 OBJECT-TYPE
SYNTAX INTEGER (0..65535)
ACCESS read-only
STATUS optional
DESCRIPTION
        " "
::= { outlet24PDU6 6 }

switch25PDU6 OBJECT-TYPE
SYNTAX INTEGER (0..3)
ACCESS read-write
STATUS optional
DESCRIPTION
        " "
::= { outlet25PDU6 1 }

voltage25PDU6 OBJECT-TYPE
SYNTAX INTEGER (0..65535)
ACCESS read-only
STATUS optional
DESCRIPTION
        " "
::= { outlet25PDU6 2 }

current25PDU6 OBJECT-TYPE
SYNTAX INTEGER (0..65535)
ACCESS read-only
STATUS optional
DESCRIPTION
        " "
::= { outlet25PDU6 3 }

power25PDU6 OBJECT-TYPE
SYNTAX INTEGER (0..65535)
ACCESS read-only
STATUS optional
DESCRIPTION
        " "
::= { outlet25PDU6 4 }

pf25PDU6 OBJECT-TYPE
SYNTAX INTEGER (0..65535)
ACCESS read-only
STATUS optional
DESCRIPTION
        " "
::= { outlet25PDU6 5 }

energy25PDU6 OBJECT-TYPE
SYNTAX INTEGER (0..65535)
ACCESS read-only
STATUS optional
DESCRIPTION
        " "
::= { outlet25PDU6 6 }

switch26PDU6 OBJECT-TYPE
SYNTAX INTEGER (0..3)
ACCESS read-write
STATUS optional
DESCRIPTION
        " "
::= { outlet26PDU6 1 }

voltage26PDU6 OBJECT-TYPE
SYNTAX INTEGER (0..65535)
ACCESS read-only
STATUS optional
DESCRIPTION
        " "
::= { outlet26PDU6 2 }

current26PDU6 OBJECT-TYPE
SYNTAX INTEGER (0..65535)
ACCESS read-only
STATUS optional
DESCRIPTION
        " "
::= { outlet26PDU6 3 }

power26PDU6 OBJECT-TYPE
SYNTAX INTEGER (0..65535)
ACCESS read-only
STATUS optional
DESCRIPTION
        " "
::= { outlet26PDU6 4 }

pf26PDU6 OBJECT-TYPE
SYNTAX INTEGER (0..65535)
ACCESS read-only
STATUS optional
DESCRIPTION
        " "
::= { outlet26PDU6 5 }

energy26PDU6 OBJECT-TYPE
SYNTAX INTEGER (0..65535)
ACCESS read-only
STATUS optional
DESCRIPTION
        " "
::= { outlet26PDU6 6 }

switch27PDU6 OBJECT-TYPE
SYNTAX INTEGER (0..3)
ACCESS read-write
STATUS optional
DESCRIPTION
        " "
::= { outlet27PDU6 1 }

voltage27PDU6 OBJECT-TYPE
SYNTAX INTEGER (0..65535)
ACCESS read-only
STATUS optional
DESCRIPTION
        " "
::= { outlet27PDU6 2 }

current27PDU6 OBJECT-TYPE
SYNTAX INTEGER (0..65535)
ACCESS read-only
STATUS optional
DESCRIPTION
        " "
::= { outlet27PDU6 3 }

power27PDU6 OBJECT-TYPE
SYNTAX INTEGER (0..65535)
ACCESS read-only
STATUS optional
DESCRIPTION
        " "
::= { outlet27PDU6 4 }

pf27PDU6 OBJECT-TYPE
SYNTAX INTEGER (0..65535)
ACCESS read-only
STATUS optional
DESCRIPTION
        " "
::= { outlet27PDU6 5 }

energy27PDU6 OBJECT-TYPE
SYNTAX INTEGER (0..65535)
ACCESS read-only
STATUS optional
DESCRIPTION
        " "
::= { outlet27PDU6 6 }

switch28PDU6 OBJECT-TYPE
SYNTAX INTEGER (0..3)
ACCESS read-write
STATUS optional
DESCRIPTION
        " "
::= { outlet28PDU6 1 }

voltage28PDU6 OBJECT-TYPE
SYNTAX INTEGER (0..65535)
ACCESS read-only
STATUS optional
DESCRIPTION
        " "
::= { outlet28PDU6 2 }

current28PDU6 OBJECT-TYPE
SYNTAX INTEGER (0..65535)
ACCESS read-only
STATUS optional
DESCRIPTION
        " "
::= { outlet28PDU6 3 }

power28PDU6 OBJECT-TYPE
SYNTAX INTEGER (0..65535)
ACCESS read-only
STATUS optional
DESCRIPTION
        " "
::= { outlet28PDU6 4 }

pf28PDU6 OBJECT-TYPE
SYNTAX INTEGER (0..65535)
ACCESS read-only
STATUS optional
DESCRIPTION
        " "
::= { outlet28PDU6 5 }

energy28PDU6 OBJECT-TYPE
SYNTAX INTEGER (0..65535)
ACCESS read-only
STATUS optional
DESCRIPTION
        " "
::= { outlet28PDU6 6 }

switch29PDU6 OBJECT-TYPE
SYNTAX INTEGER (0..3)
ACCESS read-write
STATUS optional
DESCRIPTION
        " "
::= { outlet29PDU6 1 }

voltage29PDU6 OBJECT-TYPE
SYNTAX INTEGER (0..65535)
ACCESS read-only
STATUS optional
DESCRIPTION
        " "
::= { outlet29PDU6 2 }

current29PDU6 OBJECT-TYPE
SYNTAX INTEGER (0..65535)
ACCESS read-only
STATUS optional
DESCRIPTION
        " "
::= { outlet29PDU6 3 }

power29PDU6 OBJECT-TYPE
SYNTAX INTEGER (0..65535)
ACCESS read-only
STATUS optional
DESCRIPTION
        " "
::= { outlet29PDU6 4 }

pf29PDU6 OBJECT-TYPE
SYNTAX INTEGER (0..65535)
ACCESS read-only
STATUS optional
DESCRIPTION
        " "
::= { outlet29PDU6 5 }

energy29PDU6 OBJECT-TYPE
SYNTAX INTEGER (0..65535)
ACCESS read-only
STATUS optional
DESCRIPTION
        " "
::= { outlet29PDU6 6 }

switch30PDU6 OBJECT-TYPE
SYNTAX INTEGER (0..3)
ACCESS read-write
STATUS optional
DESCRIPTION
        " "
::= { outlet30PDU6 1 }

voltage30PDU6 OBJECT-TYPE
SYNTAX INTEGER (0..65535)
ACCESS read-only
STATUS optional
DESCRIPTION
        " "
::= { outlet30PDU6 2 }

current30PDU6 OBJECT-TYPE
SYNTAX INTEGER (0..65535)
ACCESS read-only
STATUS optional
DESCRIPTION
        " "
::= { outlet30PDU6 3 }

power30PDU6 OBJECT-TYPE
SYNTAX INTEGER (0..65535)
ACCESS read-only
STATUS optional
DESCRIPTION
        " "
::= { outlet30PDU6 4 }

pf30PDU6 OBJECT-TYPE
SYNTAX INTEGER (0..65535)
ACCESS read-only
STATUS optional
DESCRIPTION
        " "
::= { outlet30PDU6 5 }

energy30PDU6 OBJECT-TYPE
SYNTAX INTEGER (0..65535)
ACCESS read-only
STATUS optional
DESCRIPTION
        " "
::= { outlet30PDU6 6 }

switch31PDU6 OBJECT-TYPE
SYNTAX INTEGER (0..3)
ACCESS read-write
STATUS optional
DESCRIPTION
        " "
::= { outlet31PDU6 1 }

voltage31PDU6 OBJECT-TYPE
SYNTAX INTEGER (0..65535)
ACCESS read-only
STATUS optional
DESCRIPTION
        " "
::= { outlet31PDU6 2 }

current31PDU6 OBJECT-TYPE
SYNTAX INTEGER (0..65535)
ACCESS read-only
STATUS optional
DESCRIPTION
        " "
::= { outlet31PDU6 3 }

power31PDU6 OBJECT-TYPE
SYNTAX INTEGER (0..65535)
ACCESS read-only
STATUS optional
DESCRIPTION
        " "
::= { outlet31PDU6 4 }

pf31PDU6 OBJECT-TYPE
SYNTAX INTEGER (0..65535)
ACCESS read-only
STATUS optional
DESCRIPTION
        " "
::= { outlet31PDU6 5 }

energy31PDU6 OBJECT-TYPE
SYNTAX INTEGER (0..65535)
ACCESS read-only
STATUS optional
DESCRIPTION
        " "
::= { outlet31PDU6 6 }

switch32PDU6 OBJECT-TYPE
SYNTAX INTEGER (0..3)
ACCESS read-write
STATUS optional
DESCRIPTION
        " "
::= { outlet32PDU6 1 }

voltage32PDU6 OBJECT-TYPE
SYNTAX INTEGER (0..65535)
ACCESS read-only
STATUS optional
DESCRIPTION
        " "
::= { outlet32PDU6 2 }

current32PDU6 OBJECT-TYPE
SYNTAX INTEGER (0..65535)
ACCESS read-only
STATUS optional
DESCRIPTION
        " "
::= { outlet32PDU6 3 }

power32PDU6 OBJECT-TYPE
SYNTAX INTEGER (0..65535)
ACCESS read-only
STATUS optional
DESCRIPTION
        " "
::= { outlet32PDU6 4 }

pf32PDU6 OBJECT-TYPE
SYNTAX INTEGER (0..65535)
ACCESS read-only
STATUS optional
DESCRIPTION
        " "
::= { outlet32PDU6 5 }

energy32PDU6 OBJECT-TYPE
SYNTAX INTEGER (0..65535)
ACCESS read-only
STATUS optional
DESCRIPTION
        " "
::= { outlet32PDU6 6 }

switch33PDU6 OBJECT-TYPE
SYNTAX INTEGER (0..3)
ACCESS read-write
STATUS optional
DESCRIPTION
        " "
::= { outlet33PDU6 1 }

voltage33PDU6 OBJECT-TYPE
SYNTAX INTEGER (0..65535)
ACCESS read-only
STATUS optional
DESCRIPTION
        " "
::= { outlet33PDU6 2 }

current33PDU6 OBJECT-TYPE
SYNTAX INTEGER (0..65535)
ACCESS read-only
STATUS optional
DESCRIPTION
        " "
::= { outlet33PDU6 3 }

power33PDU6 OBJECT-TYPE
SYNTAX INTEGER (0..65535)
ACCESS read-only
STATUS optional
DESCRIPTION
        " "
::= { outlet33PDU6 4 }

pf33PDU6 OBJECT-TYPE
SYNTAX INTEGER (0..65535)
ACCESS read-only
STATUS optional
DESCRIPTION
        " "
::= { outlet33PDU6 5 }

energy33PDU6 OBJECT-TYPE
SYNTAX INTEGER (0..65535)
ACCESS read-only
STATUS optional
DESCRIPTION
        " "
::= { outlet33PDU6 6 }

switch34PDU6 OBJECT-TYPE
SYNTAX INTEGER (0..3)
ACCESS read-write
STATUS optional
DESCRIPTION
        " "
::= { outlet34PDU6 1 }

voltage34PDU6 OBJECT-TYPE
SYNTAX INTEGER (0..65535)
ACCESS read-only
STATUS optional
DESCRIPTION
        " "
::= { outlet34PDU6 2 }

current34PDU6 OBJECT-TYPE
SYNTAX INTEGER (0..65535)
ACCESS read-only
STATUS optional
DESCRIPTION
        " "
::= { outlet34PDU6 3 }

power34PDU6 OBJECT-TYPE
SYNTAX INTEGER (0..65535)
ACCESS read-only
STATUS optional
DESCRIPTION
        " "
::= { outlet34PDU6 4 }

pf34PDU6 OBJECT-TYPE
SYNTAX INTEGER (0..65535)
ACCESS read-only
STATUS optional
DESCRIPTION
        " "
::= { outlet34PDU6 5 }

energy34PDU6 OBJECT-TYPE
SYNTAX INTEGER (0..65535)
ACCESS read-only
STATUS optional
DESCRIPTION
        " "
::= { outlet34PDU6 6 }

switch35PDU6 OBJECT-TYPE
SYNTAX INTEGER (0..3)
ACCESS read-write
STATUS optional
DESCRIPTION
        " "
::= { outlet35PDU6 1 }

voltage35PDU6 OBJECT-TYPE
SYNTAX INTEGER (0..65535)
ACCESS read-only
STATUS optional
DESCRIPTION
        " "
::= { outlet35PDU6 2 }

current35PDU6 OBJECT-TYPE
SYNTAX INTEGER (0..65535)
ACCESS read-only
STATUS optional
DESCRIPTION
        " "
::= { outlet35PDU6 3 }

power35PDU6 OBJECT-TYPE
SYNTAX INTEGER (0..65535)
ACCESS read-only
STATUS optional
DESCRIPTION
        " "
::= { outlet35PDU6 4 }

pf35PDU6 OBJECT-TYPE
SYNTAX INTEGER (0..65535)
ACCESS read-only
STATUS optional
DESCRIPTION
        " "
::= { outlet35PDU6 5 }

energy35PDU6 OBJECT-TYPE
SYNTAX INTEGER (0..65535)
ACCESS read-only
STATUS optional
DESCRIPTION
        " "
::= { outlet35PDU6 6 }

switch36PDU6 OBJECT-TYPE
SYNTAX INTEGER (0..3)
ACCESS read-write
STATUS optional
DESCRIPTION
        " "
::= { outlet36PDU6 1 }

voltage36PDU6 OBJECT-TYPE
SYNTAX INTEGER (0..65535)
ACCESS read-only
STATUS optional
DESCRIPTION
        " "
::= { outlet36PDU6 2 }

current36PDU6 OBJECT-TYPE
SYNTAX INTEGER (0..65535)
ACCESS read-only
STATUS optional
DESCRIPTION
        " "
::= { outlet36PDU6 3 }

power36PDU6 OBJECT-TYPE
SYNTAX INTEGER (0..65535)
ACCESS read-only
STATUS optional
DESCRIPTION
        " "
::= { outlet36PDU6 4 }

pf36PDU6 OBJECT-TYPE
SYNTAX INTEGER (0..65535)
ACCESS read-only
STATUS optional
DESCRIPTION
        " "
::= { outlet36PDU6 5 }

energy36PDU6 OBJECT-TYPE
SYNTAX INTEGER (0..65535)
ACCESS read-only
STATUS optional
DESCRIPTION
        " "
::= { outlet36PDU6 6 }

sensor1 OBJECT IDENTIFIER ::= { pdu6 4 }

temperature1PDU6 OBJECT-TYPE
SYNTAX INTEGER (0..65535)
ACCESS read-only
STATUS optional
DESCRIPTION
        " "
::= { sensor1 1 }

humidity1PDU6 OBJECT-TYPE
SYNTAX INTEGER (0..65535)
ACCESS read-only
STATUS optional
DESCRIPTION
        " "
::= { sensor1 2 }

temperature2PDU6 OBJECT-TYPE
SYNTAX INTEGER (0..65535)
ACCESS read-only
STATUS optional
DESCRIPTION
        " "
::= { sensor1 3 }

humidity2PDU6 OBJECT-TYPE
SYNTAX INTEGER (0..65535)
ACCESS read-only
STATUS optional
DESCRIPTION
        " "
::= { sensor1 4 }

inputStatus1PDU6 OBJECT-TYPE
SYNTAX INTEGER (0..1)
ACCESS read-only
STATUS optional
DESCRIPTION
        " "
::= { sensor1 5 }

inputStatus2PDU6 OBJECT-TYPE
SYNTAX INTEGER (0..1)
ACCESS read-only
STATUS optional
DESCRIPTION
        " "
::= { sensor1 6 }

inputStatus3PDU6 OBJECT-TYPE
SYNTAX INTEGER (0..1)
ACCESS read-only
STATUS optional
DESCRIPTION
        " "
::= { sensor1 7 }

inputStatus4PDU6 OBJECT-TYPE
SYNTAX INTEGER (0..1)
ACCESS read-only
STATUS optional
DESCRIPTION
        " "
::= { sensor1 8 }

doStatus1PDU6 OBJECT-TYPE
SYNTAX INTEGER (0..1)
ACCESS read-only
STATUS optional
DESCRIPTION
        " "
::= { sensor1 9 }

doStatus2PDU6 OBJECT-TYPE
SYNTAX INTEGER (0..1)
ACCESS read-only
STATUS optional
DESCRIPTION
        " "
::= { sensor1 10 }

baseinfo1 OBJECT IDENTIFIER ::= { pdu7 1 }

cascadeAlarmPDU7 OBJECT-TYPE
SYNTAX INTEGER (0..3)
ACCESS read-only
STATUS optional
DESCRIPTION
        " "
::= { baseinfo1 1 }

deviceNamePDU7 OBJECT-TYPE
SYNTAX DisplayString (SIZE (32))
ACCESS read-write
STATUS optional
DESCRIPTION
        " "
::= { baseinfo1 2 }

outletNumberPDU7 OBJECT-TYPE
SYNTAX INTEGER (0..36)
ACCESS read-only
STATUS optional
DESCRIPTION
        " "
::= { baseinfo1 3 }

temphum1WarnStatPDU7 OBJECT-TYPE
SYNTAX INTEGER (0..127)
ACCESS read-only
STATUS optional
DESCRIPTION
        " "
::= { baseinfo1 4 }

temphum2WarnStatPDU7 OBJECT-TYPE
SYNTAX INTEGER (0..127)
ACCESS read-only
STATUS optional
DESCRIPTION
        " "
::= { baseinfo1 5 }

input1WarnStatPDU7 OBJECT-TYPE
SYNTAX INTEGER (0..1)
ACCESS read-only
STATUS optional
DESCRIPTION
        " "
::= { baseinfo1 6 }

input2WarnStatPDU7 OBJECT-TYPE
SYNTAX INTEGER (0..1)
ACCESS read-only
STATUS optional
DESCRIPTION
        " "
::= { baseinfo1 7 }

input3WarnStatPDU7 OBJECT-TYPE
SYNTAX INTEGER (0..1)
ACCESS read-only
STATUS optional
DESCRIPTION
        " "
::= { baseinfo1 8 }

input4WarnStatPDU7 OBJECT-TYPE
SYNTAX INTEGER (0..1)
ACCESS read-only
STATUS optional
DESCRIPTION
        " "
::= { baseinfo1 9 }

currentL1WarnStatPDU7 OBJECT-TYPE
SYNTAX INTEGER (0..127)
ACCESS read-only
STATUS optional
DESCRIPTION
        " "
::= { baseinfo1 10 }

currentL2WarnStatPDU7 OBJECT-TYPE
SYNTAX INTEGER (0..127)
ACCESS read-only
STATUS optional
DESCRIPTION
        " "
::= { baseinfo1 11 }

currentL3WarnStatPDU7 OBJECT-TYPE
SYNTAX INTEGER (0..127)
ACCESS read-only
STATUS optional
DESCRIPTION
        " "
::= { baseinfo1 12 }

voltageL1WarnStatPDU7 OBJECT-TYPE
SYNTAX INTEGER (0..127)
ACCESS read-only
STATUS optional
DESCRIPTION
        " "
::= { baseinfo1 13 }

voltageL2WarnStatPDU7 OBJECT-TYPE
SYNTAX INTEGER (0..127)
ACCESS read-only
STATUS optional
DESCRIPTION
        " "
::= { baseinfo1 14 }

voltageL3WarnStatPDU7 OBJECT-TYPE
SYNTAX INTEGER (0..127)
ACCESS read-only
STATUS optional
DESCRIPTION
        " "
::= { baseinfo1 15 }

outlet1WarnStatPDU7 OBJECT-TYPE
SYNTAX INTEGER (0..127)
ACCESS read-only
STATUS optional
DESCRIPTION
        " "
::= { baseinfo1 16 }

outlet2WarnStatPDU7 OBJECT-TYPE
SYNTAX INTEGER (0..127)
ACCESS read-only
STATUS optional
DESCRIPTION
        " "
::= { baseinfo1 17 }

outlet3WarnStatPDU7 OBJECT-TYPE
SYNTAX INTEGER (0..127)
ACCESS read-only
STATUS optional
DESCRIPTION
        " "
::= { baseinfo1 18 }

outlet4WarnStatPDU7 OBJECT-TYPE
SYNTAX INTEGER (0..127)
ACCESS read-only
STATUS optional
DESCRIPTION
        " "
::= { baseinfo1 19 }

outlet5WarnStatPDU7 OBJECT-TYPE
SYNTAX INTEGER (0..127)
ACCESS read-only
STATUS optional
DESCRIPTION
        " "
::= { baseinfo1 20 }

outlet6WarnStatPDU7 OBJECT-TYPE
SYNTAX INTEGER (0..127)
ACCESS read-only
STATUS optional
DESCRIPTION
        " "
::= { baseinfo1 21 }

outlet7WarnStatPDU7 OBJECT-TYPE
SYNTAX INTEGER (0..127)
ACCESS read-only
STATUS optional
DESCRIPTION
        " "
::= { baseinfo1 22 }

outlet8WarnStatPDU7 OBJECT-TYPE
SYNTAX INTEGER (0..127)
ACCESS read-only
STATUS optional
DESCRIPTION
        " "
::= { baseinfo1 23 }

outlet9WarnStatPDU7 OBJECT-TYPE
SYNTAX INTEGER (0..127)
ACCESS read-only
STATUS optional
DESCRIPTION
        " "
::= { baseinfo1 24 }

outlet10WarnStatPDU7 OBJECT-TYPE
SYNTAX INTEGER (0..127)
ACCESS read-only
STATUS optional
DESCRIPTION
        " "
::= { baseinfo1 25 }

outlet11WarnStatPDU7 OBJECT-TYPE
SYNTAX INTEGER (0..127)
ACCESS read-only
STATUS optional
DESCRIPTION
        " "
::= { baseinfo1 26 }

outlet12WarnStatPDU7 OBJECT-TYPE
SYNTAX INTEGER (0..127)
ACCESS read-only
STATUS optional
DESCRIPTION
        " "
::= { baseinfo1 27 }

outlet13WarnStatPDU7 OBJECT-TYPE
SYNTAX INTEGER (0..127)
ACCESS read-only
STATUS optional
DESCRIPTION
        " "
::= { baseinfo1 28 }

outlet14WarnStatPDU7 OBJECT-TYPE
SYNTAX INTEGER (0..127)
ACCESS read-only
STATUS optional
DESCRIPTION
        " "
::= { baseinfo1 29 }

outlet15WarnStatPDU7 OBJECT-TYPE
SYNTAX INTEGER (0..127)
ACCESS read-only
STATUS optional
DESCRIPTION
        " "
::= { baseinfo1 30 }

outlet16WarnStatPDU7 OBJECT-TYPE
SYNTAX INTEGER (0..127)
ACCESS read-only
STATUS optional
DESCRIPTION
        " "
::= { baseinfo1 31 }

outlet17WarnStatPDU7 OBJECT-TYPE
SYNTAX INTEGER (0..127)
ACCESS read-only
STATUS optional
DESCRIPTION
        " "
::= { baseinfo1 32 }

outlet18WarnStatPDU7 OBJECT-TYPE
SYNTAX INTEGER (0..127)
ACCESS read-only
STATUS optional
DESCRIPTION
        " "
::= { baseinfo1 33 }

outlet19WarnStatPDU7 OBJECT-TYPE
SYNTAX INTEGER (0..127)
ACCESS read-only
STATUS optional
DESCRIPTION
        " "
::= { baseinfo1 34 }

outlet20WarnStatPDU7 OBJECT-TYPE
SYNTAX INTEGER (0..127)
ACCESS read-only
STATUS optional
DESCRIPTION
        " "
::= { baseinfo1 35 }

outlet21WarnStatPDU7 OBJECT-TYPE
SYNTAX INTEGER (0..127)
ACCESS read-only
STATUS optional
DESCRIPTION
        " "
::= { baseinfo1 36 }

outlet22WarnStatPDU7 OBJECT-TYPE
SYNTAX INTEGER (0..127)
ACCESS read-only
STATUS optional
DESCRIPTION
        " "
::= { baseinfo1 37 }

outlet23WarnStatPDU7 OBJECT-TYPE
SYNTAX INTEGER (0..127)
ACCESS read-only
STATUS optional
DESCRIPTION
        " "
::= { baseinfo1 38 }

outlet24WarnStatPDU7 OBJECT-TYPE
SYNTAX INTEGER (0..127)
ACCESS read-only
STATUS optional
DESCRIPTION
        " "
::= { baseinfo1 39 }

outlet25WarnStatPDU7 OBJECT-TYPE
SYNTAX INTEGER (0..127)
ACCESS read-only
STATUS optional
DESCRIPTION
        " "
::= { baseinfo1 40 }

outlet26WarnStatPDU7 OBJECT-TYPE
SYNTAX INTEGER (0..127)
ACCESS read-only
STATUS optional
DESCRIPTION
        " "
::= { baseinfo1 41 }

outlet27WarnStatPDU7 OBJECT-TYPE
SYNTAX INTEGER (0..127)
ACCESS read-only
STATUS optional
DESCRIPTION
        " "
::= { baseinfo1 42 }

outlet28WarnStatPDU7 OBJECT-TYPE
SYNTAX INTEGER (0..127)
ACCESS read-only
STATUS optional
DESCRIPTION
        " "
::= { baseinfo1 43 }

outlet29WarnStatPDU7 OBJECT-TYPE
SYNTAX INTEGER (0..127)
ACCESS read-only
STATUS optional
DESCRIPTION
        " "
::= { baseinfo1 44 }

outlet30WarnStatPDU7 OBJECT-TYPE
SYNTAX INTEGER (0..127)
ACCESS read-only
STATUS optional
DESCRIPTION
        " "
::= { baseinfo1 45 }

outlet31WarnStatPDU7 OBJECT-TYPE
SYNTAX INTEGER (0..127)
ACCESS read-only
STATUS optional
DESCRIPTION
        " "
::= { baseinfo1 46 }

outlet32WarnStatPDU7 OBJECT-TYPE
SYNTAX INTEGER (0..127)
ACCESS read-only
STATUS optional
DESCRIPTION
        " "
::= { baseinfo1 47 }

outlet33WarnStatPDU7 OBJECT-TYPE
SYNTAX INTEGER (0..127)
ACCESS read-only
STATUS optional
DESCRIPTION
        " "
::= { baseinfo1 48 }

outlet34WarnStatPDU7 OBJECT-TYPE
SYNTAX INTEGER (0..127)
ACCESS read-only
STATUS optional
DESCRIPTION
        " "
::= { baseinfo1 49 }

outlet35WarnStatPDU7 OBJECT-TYPE
SYNTAX INTEGER (0..127)
ACCESS read-only
STATUS optional
DESCRIPTION
        " "
::= { baseinfo1 50 }

outlet36WarnStatPDU7 OBJECT-TYPE
SYNTAX INTEGER (0..127)
ACCESS read-only
STATUS optional
DESCRIPTION
        " "
::= { baseinfo1 51 }

input1 OBJECT IDENTIFIER ::= { pdu7 2 }

currentL1PDU7 OBJECT-TYPE
SYNTAX INTEGER (0..65535)
ACCESS read-only
STATUS optional
DESCRIPTION
        " "
::= { input1 1 }

voltageL1PDU7 OBJECT-TYPE
SYNTAX INTEGER (0..65535)
ACCESS read-only
STATUS optional
DESCRIPTION
        " "
::= { input1 2 }

powerL1PDU7 OBJECT-TYPE
SYNTAX INTEGER (0..65535)
ACCESS read-only
STATUS optional
DESCRIPTION
        " "
::= { input1 3 }

pfL1PDU7 OBJECT-TYPE
SYNTAX INTEGER (0..65535)
ACCESS read-only
STATUS optional
DESCRIPTION
        " "
::= { input1 4 }

energyL1PDU7 OBJECT-TYPE
SYNTAX INTEGER (0..65535)
ACCESS read-only
STATUS optional
DESCRIPTION
        " "
::= { input1 5 }

currentL2PDU7 OBJECT-TYPE
SYNTAX INTEGER (0..65535)
ACCESS read-only
STATUS optional
DESCRIPTION
        " "
::= { input1 6 }

voltageL2PDU7 OBJECT-TYPE
SYNTAX INTEGER (0..65535)
ACCESS read-only
STATUS optional
DESCRIPTION
        " "
::= { input1 7 }

powerL2PDU7 OBJECT-TYPE
SYNTAX INTEGER (0..65535)
ACCESS read-only
STATUS optional
DESCRIPTION
        " "
::= { input1 8 }

pfL2PDU7 OBJECT-TYPE
SYNTAX INTEGER (0..65535)
ACCESS read-only
STATUS optional
DESCRIPTION
        " "
::= { input1 9 }

energyL2PDU7 OBJECT-TYPE
SYNTAX INTEGER (0..65535)
ACCESS read-only
STATUS optional
DESCRIPTION
        " "
::= { input1 10 }

currentL3PDU7 OBJECT-TYPE
SYNTAX INTEGER (0..65535)
ACCESS read-only
STATUS optional
DESCRIPTION
        " "
::= { input1 11 }

voltageL3PDU7 OBJECT-TYPE
SYNTAX INTEGER (0..65535)
ACCESS read-only
STATUS optional
DESCRIPTION
        " "
::= { input1 12 }

powerL3PDU7 OBJECT-TYPE
SYNTAX INTEGER (0..65535)
ACCESS read-only
STATUS optional
DESCRIPTION
        " "
::= { input1 13 }

pfL3PDU7 OBJECT-TYPE
SYNTAX INTEGER (0..65535)
ACCESS read-only
STATUS optional
DESCRIPTION
        " "
::= { input1 14 }

energyL3PDU7 OBJECT-TYPE
SYNTAX INTEGER (0..65535)
ACCESS read-only
STATUS optional
DESCRIPTION
        " "
::= { input1 15 }

outletinfo1 OBJECT IDENTIFIER ::= { pdu7 3 }

outlet1PDU7 OBJECT IDENTIFIER ::= { outletinfo1 1 }

outlet2PDU7 OBJECT IDENTIFIER ::= { outletinfo1 2 }

outlet3PDU7 OBJECT IDENTIFIER ::= { outletinfo1 3 }

outlet4PDU7 OBJECT IDENTIFIER ::= { outletinfo1 4 }

outlet5PDU7 OBJECT IDENTIFIER ::= { outletinfo1 5 }

outlet6PDU7 OBJECT IDENTIFIER ::= { outletinfo1 6 }

outlet7PDU7 OBJECT IDENTIFIER ::= { outletinfo1 7 }

outlet8PDU7 OBJECT IDENTIFIER ::= { outletinfo1 8 }

outlet9PDU7 OBJECT IDENTIFIER ::= { outletinfo1 9 }

outlet10PDU7 OBJECT IDENTIFIER ::= { outletinfo1 10 }

outlet11PDU7 OBJECT IDENTIFIER ::= { outletinfo1 11 }

outlet12PDU7 OBJECT IDENTIFIER ::= { outletinfo1 12 }

outlet13PDU7 OBJECT IDENTIFIER ::= { outletinfo1 13 }

outlet14PDU7 OBJECT IDENTIFIER ::= { outletinfo1 14 }

outlet15PDU7 OBJECT IDENTIFIER ::= { outletinfo1 15 }

outlet16PDU7 OBJECT IDENTIFIER ::= { outletinfo1 16 }

outlet17PDU7 OBJECT IDENTIFIER ::= { outletinfo1 17 }

outlet18PDU7 OBJECT IDENTIFIER ::= { outletinfo1 18 }

outlet19PDU7 OBJECT IDENTIFIER ::= { outletinfo1 19 }

outlet20PDU7 OBJECT IDENTIFIER ::= { outletinfo1 20 }

outlet21PDU7 OBJECT IDENTIFIER ::= { outletinfo1 21 }

outlet22PDU7 OBJECT IDENTIFIER ::= { outletinfo1 22 }

outlet23PDU7 OBJECT IDENTIFIER ::= { outletinfo1 23 }

outlet24PDU7 OBJECT IDENTIFIER ::= { outletinfo1 24 }

outlet25PDU7 OBJECT IDENTIFIER ::= { outletinfo1 25 }

outlet26PDU7 OBJECT IDENTIFIER ::= { outletinfo1 26 }

outlet27PDU7 OBJECT IDENTIFIER ::= { outletinfo1 27 }

outlet28PDU7 OBJECT IDENTIFIER ::= { outletinfo1 28 }

outlet29PDU7 OBJECT IDENTIFIER ::= { outletinfo1 29 }

outlet30PDU7 OBJECT IDENTIFIER ::= { outletinfo1 30 }

outlet31PDU7 OBJECT IDENTIFIER ::= { outletinfo1 31 }

outlet32PDU7 OBJECT IDENTIFIER ::= { outletinfo1 32 }

outlet33PDU7 OBJECT IDENTIFIER ::= { outletinfo1 33 }

outlet34PDU7 OBJECT IDENTIFIER ::= { outletinfo1 34 }

outlet35PDU7 OBJECT IDENTIFIER ::= { outletinfo1 35 }

outlet36PDU7 OBJECT IDENTIFIER ::= { outletinfo1 36 }

switch1PDU7 OBJECT-TYPE
SYNTAX INTEGER (0..3)
ACCESS read-write
STATUS optional
DESCRIPTION
        " "
::= { outlet1PDU7 1 }

voltage1PDU7 OBJECT-TYPE
SYNTAX INTEGER (0..65535)
ACCESS read-only
STATUS optional
DESCRIPTION
        " "
::= { outlet1PDU7 2 }

current1PDU7 OBJECT-TYPE
SYNTAX INTEGER (0..65535)
ACCESS read-only
STATUS optional
DESCRIPTION
        " "
::= { outlet1PDU7 3 }

power1PDU7 OBJECT-TYPE
SYNTAX INTEGER (0..65535)
ACCESS read-only
STATUS optional
DESCRIPTION
        " "
::= { outlet1PDU7 4 }

pf1PDU7 OBJECT-TYPE
SYNTAX INTEGER (0..65535)
ACCESS read-only
STATUS optional
DESCRIPTION
        " "
::= { outlet1PDU7 5 }

energy1PDU7 OBJECT-TYPE
SYNTAX INTEGER (0..65535)
ACCESS read-only
STATUS optional
DESCRIPTION
        " "
::= { outlet1PDU7 6 }

switch2PDU7 OBJECT-TYPE
SYNTAX INTEGER (0..3)
ACCESS read-write
STATUS optional
DESCRIPTION
        " "
::= { outlet2PDU7 1 }

voltage2PDU7 OBJECT-TYPE
SYNTAX INTEGER (0..65535)
ACCESS read-only
STATUS optional
DESCRIPTION
        " "
::= { outlet2PDU7 2 }

current2PDU7 OBJECT-TYPE
SYNTAX INTEGER (0..65535)
ACCESS read-only
STATUS optional
DESCRIPTION
        " "
::= { outlet2PDU7 3 }

power2PDU7 OBJECT-TYPE
SYNTAX INTEGER (0..65535)
ACCESS read-only
STATUS optional
DESCRIPTION
        " "
::= { outlet2PDU7 4 }

pf2PDU7 OBJECT-TYPE
SYNTAX INTEGER (0..65535)
ACCESS read-only
STATUS optional
DESCRIPTION
        " "
::= { outlet2PDU7 5 }

energy2PDU7 OBJECT-TYPE
SYNTAX INTEGER (0..65535)
ACCESS read-only
STATUS optional
DESCRIPTION
        " "
::= { outlet2PDU7 6 }

switch3PDU7 OBJECT-TYPE
SYNTAX INTEGER (0..3)
ACCESS read-write
STATUS optional
DESCRIPTION
        " "
::= { outlet3PDU7 1 }

voltage3PDU7 OBJECT-TYPE
SYNTAX INTEGER (0..65535)
ACCESS read-only
STATUS optional
DESCRIPTION
        " "
::= { outlet3PDU7 2 }

current3PDU7 OBJECT-TYPE
SYNTAX INTEGER (0..65535)
ACCESS read-only
STATUS optional
DESCRIPTION
        " "
::= { outlet3PDU7 3 }

power3PDU7 OBJECT-TYPE
SYNTAX INTEGER (0..65535)
ACCESS read-only
STATUS optional
DESCRIPTION
        " "
::= { outlet3PDU7 4 }

pf3PDU7 OBJECT-TYPE
SYNTAX INTEGER (0..65535)
ACCESS read-only
STATUS optional
DESCRIPTION
        " "
::= { outlet3PDU7 5 }

energy3PDU7 OBJECT-TYPE
SYNTAX INTEGER (0..65535)
ACCESS read-only
STATUS optional
DESCRIPTION
        " "
::= { outlet3PDU7 6 }

switch4PDU7 OBJECT-TYPE
SYNTAX INTEGER (0..3)
ACCESS read-write
STATUS optional
DESCRIPTION
        " "
::= { outlet4PDU7 1 }

voltage4PDU7 OBJECT-TYPE
SYNTAX INTEGER (0..65535)
ACCESS read-only
STATUS optional
DESCRIPTION
        " "
::= { outlet4PDU7 2 }

current4PDU7 OBJECT-TYPE
SYNTAX INTEGER (0..65535)
ACCESS read-only
STATUS optional
DESCRIPTION
        " "
::= { outlet4PDU7 3 }

power4PDU7 OBJECT-TYPE
SYNTAX INTEGER (0..65535)
ACCESS read-only
STATUS optional
DESCRIPTION
        " "
::= { outlet4PDU7 4 }

pf4PDU7 OBJECT-TYPE
SYNTAX INTEGER (0..65535)
ACCESS read-only
STATUS optional
DESCRIPTION
        " "
::= { outlet4PDU7 5 }

energy4PDU7 OBJECT-TYPE
SYNTAX INTEGER (0..65535)
ACCESS read-only
STATUS optional
DESCRIPTION
        " "
::= { outlet4PDU7 6 }

switch5PDU7 OBJECT-TYPE
SYNTAX INTEGER (0..3)
ACCESS read-write
STATUS optional
DESCRIPTION
        " "
::= { outlet5PDU7 1 }

voltage5PDU7 OBJECT-TYPE
SYNTAX INTEGER (0..65535)
ACCESS read-only
STATUS optional
DESCRIPTION
        " "
::= { outlet5PDU7 2 }

current5PDU7 OBJECT-TYPE
SYNTAX INTEGER (0..65535)
ACCESS read-only
STATUS optional
DESCRIPTION
        " "
::= { outlet5PDU7 3 }

power5PDU7 OBJECT-TYPE
SYNTAX INTEGER (0..65535)
ACCESS read-only
STATUS optional
DESCRIPTION
        " "
::= { outlet5PDU7 4 }

pf5PDU7 OBJECT-TYPE
SYNTAX INTEGER (0..65535)
ACCESS read-only
STATUS optional
DESCRIPTION
        " "
::= { outlet5PDU7 5 }

energy5PDU7 OBJECT-TYPE
SYNTAX INTEGER (0..65535)
ACCESS read-only
STATUS optional
DESCRIPTION
        " "
::= { outlet5PDU7 6 }

switch6PDU7 OBJECT-TYPE
SYNTAX INTEGER (0..3)
ACCESS read-write
STATUS optional
DESCRIPTION
        " "
::= { outlet6PDU7 1 }

voltage6PDU7 OBJECT-TYPE
SYNTAX INTEGER (0..65535)
ACCESS read-only
STATUS optional
DESCRIPTION
        " "
::= { outlet6PDU7 2 }

current6PDU7 OBJECT-TYPE
SYNTAX INTEGER (0..65535)
ACCESS read-only
STATUS optional
DESCRIPTION
        " "
::= { outlet6PDU7 3 }

power6PDU7 OBJECT-TYPE
SYNTAX INTEGER (0..65535)
ACCESS read-only
STATUS optional
DESCRIPTION
        " "
::= { outlet6PDU7 4 }

pf6PDU7 OBJECT-TYPE
SYNTAX INTEGER (0..65535)
ACCESS read-only
STATUS optional
DESCRIPTION
        " "
::= { outlet6PDU7 5 }

energy6PDU7 OBJECT-TYPE
SYNTAX INTEGER (0..65535)
ACCESS read-only
STATUS optional
DESCRIPTION
        " "
::= { outlet6PDU7 6 }

switch7PDU7 OBJECT-TYPE
SYNTAX INTEGER (0..3)
ACCESS read-write
STATUS optional
DESCRIPTION
        " "
::= { outlet7PDU7 1 }

voltage7PDU7 OBJECT-TYPE
SYNTAX INTEGER (0..65535)
ACCESS read-only
STATUS optional
DESCRIPTION
        " "
::= { outlet7PDU7 2 }

current7PDU7 OBJECT-TYPE
SYNTAX INTEGER (0..65535)
ACCESS read-only
STATUS optional
DESCRIPTION
        " "
::= { outlet7PDU7 3 }

power7PDU7 OBJECT-TYPE
SYNTAX INTEGER (0..65535)
ACCESS read-only
STATUS optional
DESCRIPTION
        " "
::= { outlet7PDU7 4 }

pf7PDU7 OBJECT-TYPE
SYNTAX INTEGER (0..65535)
ACCESS read-only
STATUS optional
DESCRIPTION
        " "
::= { outlet7PDU7 5 }

energy7PDU7 OBJECT-TYPE
SYNTAX INTEGER (0..65535)
ACCESS read-only
STATUS optional
DESCRIPTION
        " "
::= { outlet7PDU7 6 }

switch8PDU7 OBJECT-TYPE
SYNTAX INTEGER (0..3)
ACCESS read-write
STATUS optional
DESCRIPTION
        " "
::= { outlet8PDU7 1 }

voltage8PDU7 OBJECT-TYPE
SYNTAX INTEGER (0..65535)
ACCESS read-only
STATUS optional
DESCRIPTION
        " "
::= { outlet8PDU7 2 }

current8PDU7 OBJECT-TYPE
SYNTAX INTEGER (0..65535)
ACCESS read-only
STATUS optional
DESCRIPTION
        " "
::= { outlet8PDU7 3 }

power8PDU7 OBJECT-TYPE
SYNTAX INTEGER (0..65535)
ACCESS read-only
STATUS optional
DESCRIPTION
        " "
::= { outlet8PDU7 4 }

pf8PDU7 OBJECT-TYPE
SYNTAX INTEGER (0..65535)
ACCESS read-only
STATUS optional
DESCRIPTION
        " "
::= { outlet8PDU7 5 }

energy8PDU7 OBJECT-TYPE
SYNTAX INTEGER (0..65535)
ACCESS read-only
STATUS optional
DESCRIPTION
        " "
::= { outlet8PDU7 6 }

switch9PDU7 OBJECT-TYPE
SYNTAX INTEGER (0..3)
ACCESS read-write
STATUS optional
DESCRIPTION
        " "
::= { outlet9PDU7 1 }

voltage9PDU7 OBJECT-TYPE
SYNTAX INTEGER (0..65535)
ACCESS read-only
STATUS optional
DESCRIPTION
        " "
::= { outlet9PDU7 2 }

current9PDU7 OBJECT-TYPE
SYNTAX INTEGER (0..65535)
ACCESS read-only
STATUS optional
DESCRIPTION
        " "
::= { outlet9PDU7 3 }

power9PDU7 OBJECT-TYPE
SYNTAX INTEGER (0..65535)
ACCESS read-only
STATUS optional
DESCRIPTION
        " "
::= { outlet9PDU7 4 }

pf9PDU7 OBJECT-TYPE
SYNTAX INTEGER (0..65535)
ACCESS read-only
STATUS optional
DESCRIPTION
        " "
::= { outlet9PDU7 5 }

energy9PDU7 OBJECT-TYPE
SYNTAX INTEGER (0..65535)
ACCESS read-only
STATUS optional
DESCRIPTION
        " "
::= { outlet9PDU7 6 }

switch10PDU7 OBJECT-TYPE
SYNTAX INTEGER (0..3)
ACCESS read-write
STATUS optional
DESCRIPTION
        " "
::= { outlet10PDU7 1 }

voltage10PDU7 OBJECT-TYPE
SYNTAX INTEGER (0..65535)
ACCESS read-only
STATUS optional
DESCRIPTION
        " "
::= { outlet10PDU7 2 }

current10PDU7 OBJECT-TYPE
SYNTAX INTEGER (0..65535)
ACCESS read-only
STATUS optional
DESCRIPTION
        " "
::= { outlet10PDU7 3 }

power10PDU7 OBJECT-TYPE
SYNTAX INTEGER (0..65535)
ACCESS read-only
STATUS optional
DESCRIPTION
        " "
::= { outlet10PDU7 4 }

pf10PDU7 OBJECT-TYPE
SYNTAX INTEGER (0..65535)
ACCESS read-only
STATUS optional
DESCRIPTION
        " "
::= { outlet10PDU7 5 }

energy10PDU7 OBJECT-TYPE
SYNTAX INTEGER (0..65535)
ACCESS read-only
STATUS optional
DESCRIPTION
        " "
::= { outlet10PDU7 6 }

switch11PDU7 OBJECT-TYPE
SYNTAX INTEGER (0..3)
ACCESS read-write
STATUS optional
DESCRIPTION
        " "
::= { outlet11PDU7 1 }

voltage11PDU7 OBJECT-TYPE
SYNTAX INTEGER (0..65535)
ACCESS read-only
STATUS optional
DESCRIPTION
        " "
::= { outlet11PDU7 2 }

current11PDU7 OBJECT-TYPE
SYNTAX INTEGER (0..65535)
ACCESS read-only
STATUS optional
DESCRIPTION
        " "
::= { outlet11PDU7 3 }

power11PDU7 OBJECT-TYPE
SYNTAX INTEGER (0..65535)
ACCESS read-only
STATUS optional
DESCRIPTION
        " "
::= { outlet11PDU7 4 }

pf11PDU7 OBJECT-TYPE
SYNTAX INTEGER (0..65535)
ACCESS read-only
STATUS optional
DESCRIPTION
        " "
::= { outlet11PDU7 5 }

energy11PDU7 OBJECT-TYPE
SYNTAX INTEGER (0..65535)
ACCESS read-only
STATUS optional
DESCRIPTION
        " "
::= { outlet11PDU7 6 }

switch12PDU7 OBJECT-TYPE
SYNTAX INTEGER (0..3)
ACCESS read-write
STATUS optional
DESCRIPTION
        " "
::= { outlet12PDU7 1 }

voltage12PDU7 OBJECT-TYPE
SYNTAX INTEGER (0..65535)
ACCESS read-only
STATUS optional
DESCRIPTION
        " "
::= { outlet12PDU7 2 }

current12PDU7 OBJECT-TYPE
SYNTAX INTEGER (0..65535)
ACCESS read-only
STATUS optional
DESCRIPTION
        " "
::= { outlet12PDU7 3 }

power12PDU7 OBJECT-TYPE
SYNTAX INTEGER (0..65535)
ACCESS read-only
STATUS optional
DESCRIPTION
        " "
::= { outlet12PDU7 4 }

pf12PDU7 OBJECT-TYPE
SYNTAX INTEGER (0..65535)
ACCESS read-only
STATUS optional
DESCRIPTION
        " "
::= { outlet12PDU7 5 }

energy12PDU7 OBJECT-TYPE
SYNTAX INTEGER (0..65535)
ACCESS read-only
STATUS optional
DESCRIPTION
        " "
::= { outlet12PDU7 6 }

switch13PDU7 OBJECT-TYPE
SYNTAX INTEGER (0..3)
ACCESS read-write
STATUS optional
DESCRIPTION
        " "
::= { outlet13PDU7 1 }

voltage13PDU7 OBJECT-TYPE
SYNTAX INTEGER (0..65535)
ACCESS read-only
STATUS optional
DESCRIPTION
        " "
::= { outlet13PDU7 2 }

current13PDU7 OBJECT-TYPE
SYNTAX INTEGER (0..65535)
ACCESS read-only
STATUS optional
DESCRIPTION
        " "
::= { outlet13PDU7 3 }

power13PDU7 OBJECT-TYPE
SYNTAX INTEGER (0..65535)
ACCESS read-only
STATUS optional
DESCRIPTION
        " "
::= { outlet13PDU7 4 }

pf13PDU7 OBJECT-TYPE
SYNTAX INTEGER (0..65535)
ACCESS read-only
STATUS optional
DESCRIPTION
        " "
::= { outlet13PDU7 5 }

energy13PDU7 OBJECT-TYPE
SYNTAX INTEGER (0..65535)
ACCESS read-only
STATUS optional
DESCRIPTION
        " "
::= { outlet13PDU7 6 }

switch14PDU7 OBJECT-TYPE
SYNTAX INTEGER (0..3)
ACCESS read-write
STATUS optional
DESCRIPTION
        " "
::= { outlet14PDU7 1 }

voltage14PDU7 OBJECT-TYPE
SYNTAX INTEGER (0..65535)
ACCESS read-only
STATUS optional
DESCRIPTION
        " "
::= { outlet14PDU7 2 }

current14PDU7 OBJECT-TYPE
SYNTAX INTEGER (0..65535)
ACCESS read-only
STATUS optional
DESCRIPTION
        " "
::= { outlet14PDU7 3 }

power14PDU7 OBJECT-TYPE
SYNTAX INTEGER (0..65535)
ACCESS read-only
STATUS optional
DESCRIPTION
        " "
::= { outlet14PDU7 4 }

pf14PDU7 OBJECT-TYPE
SYNTAX INTEGER (0..65535)
ACCESS read-only
STATUS optional
DESCRIPTION
        " "
::= { outlet14PDU7 5 }

energy14PDU7 OBJECT-TYPE
SYNTAX INTEGER (0..65535)
ACCESS read-only
STATUS optional
DESCRIPTION
        " "
::= { outlet14PDU7 6 }

switch15PDU7 OBJECT-TYPE
SYNTAX INTEGER (0..3)
ACCESS read-write
STATUS optional
DESCRIPTION
        " "
::= { outlet15PDU7 1 }

voltage15PDU7 OBJECT-TYPE
SYNTAX INTEGER (0..65535)
ACCESS read-only
STATUS optional
DESCRIPTION
        " "
::= { outlet15PDU7 2 }

current15PDU7 OBJECT-TYPE
SYNTAX INTEGER (0..65535)
ACCESS read-only
STATUS optional
DESCRIPTION
        " "
::= { outlet15PDU7 3 }

power15PDU7 OBJECT-TYPE
SYNTAX INTEGER (0..65535)
ACCESS read-only
STATUS optional
DESCRIPTION
        " "
::= { outlet15PDU7 4 }

pf15PDU7 OBJECT-TYPE
SYNTAX INTEGER (0..65535)
ACCESS read-only
STATUS optional
DESCRIPTION
        " "
::= { outlet15PDU7 5 }

energy15PDU7 OBJECT-TYPE
SYNTAX INTEGER (0..65535)
ACCESS read-only
STATUS optional
DESCRIPTION
        " "
::= { outlet15PDU7 6 }

switch16PDU7 OBJECT-TYPE
SYNTAX INTEGER (0..3)
ACCESS read-write
STATUS optional
DESCRIPTION
        " "
::= { outlet16PDU7 1 }

voltage16PDU7 OBJECT-TYPE
SYNTAX INTEGER (0..65535)
ACCESS read-only
STATUS optional
DESCRIPTION
        " "
::= { outlet16PDU7 2 }

current16PDU7 OBJECT-TYPE
SYNTAX INTEGER (0..65535)
ACCESS read-only
STATUS optional
DESCRIPTION
        " "
::= { outlet16PDU7 3 }

power16PDU7 OBJECT-TYPE
SYNTAX INTEGER (0..65535)
ACCESS read-only
STATUS optional
DESCRIPTION
        " "
::= { outlet16PDU7 4 }

pf16PDU7 OBJECT-TYPE
SYNTAX INTEGER (0..65535)
ACCESS read-only
STATUS optional
DESCRIPTION
        " "
::= { outlet16PDU7 5 }

energy16PDU7 OBJECT-TYPE
SYNTAX INTEGER (0..65535)
ACCESS read-only
STATUS optional
DESCRIPTION
        " "
::= { outlet16PDU7 6 }

switch17PDU7 OBJECT-TYPE
SYNTAX INTEGER (0..3)
ACCESS read-write
STATUS optional
DESCRIPTION
        " "
::= { outlet17PDU7 1 }

voltage17PDU7 OBJECT-TYPE
SYNTAX INTEGER (0..65535)
ACCESS read-only
STATUS optional
DESCRIPTION
        " "
::= { outlet17PDU7 2 }

current17PDU7 OBJECT-TYPE
SYNTAX INTEGER (0..65535)
ACCESS read-only
STATUS optional
DESCRIPTION
        " "
::= { outlet17PDU7 3 }

power17PDU7 OBJECT-TYPE
SYNTAX INTEGER (0..65535)
ACCESS read-only
STATUS optional
DESCRIPTION
        " "
::= { outlet17PDU7 4 }

pf17PDU7 OBJECT-TYPE
SYNTAX INTEGER (0..65535)
ACCESS read-only
STATUS optional
DESCRIPTION
        " "
::= { outlet17PDU7 5 }

energy17PDU7 OBJECT-TYPE
SYNTAX INTEGER (0..65535)
ACCESS read-only
STATUS optional
DESCRIPTION
        " "
::= { outlet17PDU7 6 }

switch18PDU7 OBJECT-TYPE
SYNTAX INTEGER (0..3)
ACCESS read-write
STATUS optional
DESCRIPTION
        " "
::= { outlet18PDU7 1 }

voltage18PDU7 OBJECT-TYPE
SYNTAX INTEGER (0..65535)
ACCESS read-only
STATUS optional
DESCRIPTION
        " "
::= { outlet18PDU7 2 }

current18PDU7 OBJECT-TYPE
SYNTAX INTEGER (0..65535)
ACCESS read-only
STATUS optional
DESCRIPTION
        " "
::= { outlet18PDU7 3 }

power18PDU7 OBJECT-TYPE
SYNTAX INTEGER (0..65535)
ACCESS read-only
STATUS optional
DESCRIPTION
        " "
::= { outlet18PDU7 4 }

pf18PDU7 OBJECT-TYPE
SYNTAX INTEGER (0..65535)
ACCESS read-only
STATUS optional
DESCRIPTION
        " "
::= { outlet18PDU7 5 }

energy18PDU7 OBJECT-TYPE
SYNTAX INTEGER (0..65535)
ACCESS read-only
STATUS optional
DESCRIPTION
        " "
::= { outlet18PDU7 6 }

switch19PDU7 OBJECT-TYPE
SYNTAX INTEGER (0..3)
ACCESS read-write
STATUS optional
DESCRIPTION
        " "
::= { outlet19PDU7 1 }

voltage19PDU7 OBJECT-TYPE
SYNTAX INTEGER (0..65535)
ACCESS read-only
STATUS optional
DESCRIPTION
        " "
::= { outlet19PDU7 2 }

current19PDU7 OBJECT-TYPE
SYNTAX INTEGER (0..65535)
ACCESS read-only
STATUS optional
DESCRIPTION
        " "
::= { outlet19PDU7 3 }

power19PDU7 OBJECT-TYPE
SYNTAX INTEGER (0..65535)
ACCESS read-only
STATUS optional
DESCRIPTION
        " "
::= { outlet19PDU7 4 }

pf19PDU7 OBJECT-TYPE
SYNTAX INTEGER (0..65535)
ACCESS read-only
STATUS optional
DESCRIPTION
        " "
::= { outlet19PDU7 5 }

energy19PDU7 OBJECT-TYPE
SYNTAX INTEGER (0..65535)
ACCESS read-only
STATUS optional
DESCRIPTION
        " "
::= { outlet19PDU7 6 }

switch20PDU7 OBJECT-TYPE
SYNTAX INTEGER (0..3)
ACCESS read-write
STATUS optional
DESCRIPTION
        " "
::= { outlet20PDU7 1 }

voltage20PDU7 OBJECT-TYPE
SYNTAX INTEGER (0..65535)
ACCESS read-only
STATUS optional
DESCRIPTION
        " "
::= { outlet20PDU7 2 }

current20PDU7 OBJECT-TYPE
SYNTAX INTEGER (0..65535)
ACCESS read-only
STATUS optional
DESCRIPTION
        " "
::= { outlet20PDU7 3 }

power20PDU7 OBJECT-TYPE
SYNTAX INTEGER (0..65535)
ACCESS read-only
STATUS optional
DESCRIPTION
        " "
::= { outlet20PDU7 4 }

pf20PDU7 OBJECT-TYPE
SYNTAX INTEGER (0..65535)
ACCESS read-only
STATUS optional
DESCRIPTION
        " "
::= { outlet20PDU7 5 }

energy20PDU7 OBJECT-TYPE
SYNTAX INTEGER (0..65535)
ACCESS read-only
STATUS optional
DESCRIPTION
        " "
::= { outlet20PDU7 6 }

switch21PDU7 OBJECT-TYPE
SYNTAX INTEGER (0..3)
ACCESS read-write
STATUS optional
DESCRIPTION
        " "
::= { outlet21PDU7 1 }

voltage21PDU7 OBJECT-TYPE
SYNTAX INTEGER (0..65535)
ACCESS read-only
STATUS optional
DESCRIPTION
        " "
::= { outlet21PDU7 2 }

current21PDU7 OBJECT-TYPE
SYNTAX INTEGER (0..65535)
ACCESS read-only
STATUS optional
DESCRIPTION
        " "
::= { outlet21PDU7 3 }

power21PDU7 OBJECT-TYPE
SYNTAX INTEGER (0..65535)
ACCESS read-only
STATUS optional
DESCRIPTION
        " "
::= { outlet21PDU7 4 }

pf21PDU7 OBJECT-TYPE
SYNTAX INTEGER (0..65535)
ACCESS read-only
STATUS optional
DESCRIPTION
        " "
::= { outlet21PDU7 5 }

energy21PDU7 OBJECT-TYPE
SYNTAX INTEGER (0..65535)
ACCESS read-only
STATUS optional
DESCRIPTION
        " "
::= { outlet21PDU7 6 }

switch22PDU7 OBJECT-TYPE
SYNTAX INTEGER (0..3)
ACCESS read-write
STATUS optional
DESCRIPTION
        " "
::= { outlet22PDU7 1 }

voltage22PDU7 OBJECT-TYPE
SYNTAX INTEGER (0..65535)
ACCESS read-only
STATUS optional
DESCRIPTION
        " "
::= { outlet22PDU7 2 }

current22PDU7 OBJECT-TYPE
SYNTAX INTEGER (0..65535)
ACCESS read-only
STATUS optional
DESCRIPTION
        " "
::= { outlet22PDU7 3 }

power22PDU7 OBJECT-TYPE
SYNTAX INTEGER (0..65535)
ACCESS read-only
STATUS optional
DESCRIPTION
        " "
::= { outlet22PDU7 4 }

pf22PDU7 OBJECT-TYPE
SYNTAX INTEGER (0..65535)
ACCESS read-only
STATUS optional
DESCRIPTION
        " "
::= { outlet22PDU7 5 }

energy22PDU7 OBJECT-TYPE
SYNTAX INTEGER (0..65535)
ACCESS read-only
STATUS optional
DESCRIPTION
        " "
::= { outlet22PDU7 6 }

switch23PDU7 OBJECT-TYPE
SYNTAX INTEGER (0..3)
ACCESS read-write
STATUS optional
DESCRIPTION
        " "
::= { outlet23PDU7 1 }

voltage23PDU7 OBJECT-TYPE
SYNTAX INTEGER (0..65535)
ACCESS read-only
STATUS optional
DESCRIPTION
        " "
::= { outlet23PDU7 2 }

current23PDU7 OBJECT-TYPE
SYNTAX INTEGER (0..65535)
ACCESS read-only
STATUS optional
DESCRIPTION
        " "
::= { outlet23PDU7 3 }

power23PDU7 OBJECT-TYPE
SYNTAX INTEGER (0..65535)
ACCESS read-only
STATUS optional
DESCRIPTION
        " "
::= { outlet23PDU7 4 }

pf23PDU7 OBJECT-TYPE
SYNTAX INTEGER (0..65535)
ACCESS read-only
STATUS optional
DESCRIPTION
        " "
::= { outlet23PDU7 5 }

energy23PDU7 OBJECT-TYPE
SYNTAX INTEGER (0..65535)
ACCESS read-only
STATUS optional
DESCRIPTION
        " "
::= { outlet23PDU7 6 }

switch24PDU7 OBJECT-TYPE
SYNTAX INTEGER (0..3)
ACCESS read-write
STATUS optional
DESCRIPTION
        " "
::= { outlet24PDU7 1 }

voltage24PDU7 OBJECT-TYPE
SYNTAX INTEGER (0..65535)
ACCESS read-only
STATUS optional
DESCRIPTION
        " "
::= { outlet24PDU7 2 }

current24PDU7 OBJECT-TYPE
SYNTAX INTEGER (0..65535)
ACCESS read-only
STATUS optional
DESCRIPTION
        " "
::= { outlet24PDU7 3 }

power24PDU7 OBJECT-TYPE
SYNTAX INTEGER (0..65535)
ACCESS read-only
STATUS optional
DESCRIPTION
        " "
::= { outlet24PDU7 4 }

pf24PDU7 OBJECT-TYPE
SYNTAX INTEGER (0..65535)
ACCESS read-only
STATUS optional
DESCRIPTION
        " "
::= { outlet24PDU7 5 }

energy24PDU7 OBJECT-TYPE
SYNTAX INTEGER (0..65535)
ACCESS read-only
STATUS optional
DESCRIPTION
        " "
::= { outlet24PDU7 6 }

switch25PDU7 OBJECT-TYPE
SYNTAX INTEGER (0..3)
ACCESS read-write
STATUS optional
DESCRIPTION
        " "
::= { outlet25PDU7 1 }

voltage25PDU7 OBJECT-TYPE
SYNTAX INTEGER (0..65535)
ACCESS read-only
STATUS optional
DESCRIPTION
        " "
::= { outlet25PDU7 2 }

current25PDU7 OBJECT-TYPE
SYNTAX INTEGER (0..65535)
ACCESS read-only
STATUS optional
DESCRIPTION
        " "
::= { outlet25PDU7 3 }

power25PDU7 OBJECT-TYPE
SYNTAX INTEGER (0..65535)
ACCESS read-only
STATUS optional
DESCRIPTION
        " "
::= { outlet25PDU7 4 }

pf25PDU7 OBJECT-TYPE
SYNTAX INTEGER (0..65535)
ACCESS read-only
STATUS optional
DESCRIPTION
        " "
::= { outlet25PDU7 5 }

energy25PDU7 OBJECT-TYPE
SYNTAX INTEGER (0..65535)
ACCESS read-only
STATUS optional
DESCRIPTION
        " "
::= { outlet25PDU7 6 }

switch26PDU7 OBJECT-TYPE
SYNTAX INTEGER (0..3)
ACCESS read-write
STATUS optional
DESCRIPTION
        " "
::= { outlet26PDU7 1 }

voltage26PDU7 OBJECT-TYPE
SYNTAX INTEGER (0..65535)
ACCESS read-only
STATUS optional
DESCRIPTION
        " "
::= { outlet26PDU7 2 }

current26PDU7 OBJECT-TYPE
SYNTAX INTEGER (0..65535)
ACCESS read-only
STATUS optional
DESCRIPTION
        " "
::= { outlet26PDU7 3 }

power26PDU7 OBJECT-TYPE
SYNTAX INTEGER (0..65535)
ACCESS read-only
STATUS optional
DESCRIPTION
        " "
::= { outlet26PDU7 4 }

pf26PDU7 OBJECT-TYPE
SYNTAX INTEGER (0..65535)
ACCESS read-only
STATUS optional
DESCRIPTION
        " "
::= { outlet26PDU7 5 }

energy26PDU7 OBJECT-TYPE
SYNTAX INTEGER (0..65535)
ACCESS read-only
STATUS optional
DESCRIPTION
        " "
::= { outlet26PDU7 6 }

switch27PDU7 OBJECT-TYPE
SYNTAX INTEGER (0..3)
ACCESS read-write
STATUS optional
DESCRIPTION
        " "
::= { outlet27PDU7 1 }

voltage27PDU7 OBJECT-TYPE
SYNTAX INTEGER (0..65535)
ACCESS read-only
STATUS optional
DESCRIPTION
        " "
::= { outlet27PDU7 2 }

current27PDU7 OBJECT-TYPE
SYNTAX INTEGER (0..65535)
ACCESS read-only
STATUS optional
DESCRIPTION
        " "
::= { outlet27PDU7 3 }

power27PDU7 OBJECT-TYPE
SYNTAX INTEGER (0..65535)
ACCESS read-only
STATUS optional
DESCRIPTION
        " "
::= { outlet27PDU7 4 }

pf27PDU7 OBJECT-TYPE
SYNTAX INTEGER (0..65535)
ACCESS read-only
STATUS optional
DESCRIPTION
        " "
::= { outlet27PDU7 5 }

energy27PDU7 OBJECT-TYPE
SYNTAX INTEGER (0..65535)
ACCESS read-only
STATUS optional
DESCRIPTION
        " "
::= { outlet27PDU7 6 }

switch28PDU7 OBJECT-TYPE
SYNTAX INTEGER (0..3)
ACCESS read-write
STATUS optional
DESCRIPTION
        " "
::= { outlet28PDU7 1 }

voltage28PDU7 OBJECT-TYPE
SYNTAX INTEGER (0..65535)
ACCESS read-only
STATUS optional
DESCRIPTION
        " "
::= { outlet28PDU7 2 }

current28PDU7 OBJECT-TYPE
SYNTAX INTEGER (0..65535)
ACCESS read-only
STATUS optional
DESCRIPTION
        " "
::= { outlet28PDU7 3 }

power28PDU7 OBJECT-TYPE
SYNTAX INTEGER (0..65535)
ACCESS read-only
STATUS optional
DESCRIPTION
        " "
::= { outlet28PDU7 4 }

pf28PDU7 OBJECT-TYPE
SYNTAX INTEGER (0..65535)
ACCESS read-only
STATUS optional
DESCRIPTION
        " "
::= { outlet28PDU7 5 }

energy28PDU7 OBJECT-TYPE
SYNTAX INTEGER (0..65535)
ACCESS read-only
STATUS optional
DESCRIPTION
        " "
::= { outlet28PDU7 6 }

switch29PDU7 OBJECT-TYPE
SYNTAX INTEGER (0..3)
ACCESS read-write
STATUS optional
DESCRIPTION
        " "
::= { outlet29PDU7 1 }

voltage29PDU7 OBJECT-TYPE
SYNTAX INTEGER (0..65535)
ACCESS read-only
STATUS optional
DESCRIPTION
        " "
::= { outlet29PDU7 2 }

current29PDU7 OBJECT-TYPE
SYNTAX INTEGER (0..65535)
ACCESS read-only
STATUS optional
DESCRIPTION
        " "
::= { outlet29PDU7 3 }

power29PDU7 OBJECT-TYPE
SYNTAX INTEGER (0..65535)
ACCESS read-only
STATUS optional
DESCRIPTION
        " "
::= { outlet29PDU7 4 }

pf29PDU7 OBJECT-TYPE
SYNTAX INTEGER (0..65535)
ACCESS read-only
STATUS optional
DESCRIPTION
        " "
::= { outlet29PDU7 5 }

energy29PDU7 OBJECT-TYPE
SYNTAX INTEGER (0..65535)
ACCESS read-only
STATUS optional
DESCRIPTION
        " "
::= { outlet29PDU7 6 }

switch30PDU7 OBJECT-TYPE
SYNTAX INTEGER (0..3)
ACCESS read-write
STATUS optional
DESCRIPTION
        " "
::= { outlet30PDU7 1 }

voltage30PDU7 OBJECT-TYPE
SYNTAX INTEGER (0..65535)
ACCESS read-only
STATUS optional
DESCRIPTION
        " "
::= { outlet30PDU7 2 }

current30PDU7 OBJECT-TYPE
SYNTAX INTEGER (0..65535)
ACCESS read-only
STATUS optional
DESCRIPTION
        " "
::= { outlet30PDU7 3 }

power30PDU7 OBJECT-TYPE
SYNTAX INTEGER (0..65535)
ACCESS read-only
STATUS optional
DESCRIPTION
        " "
::= { outlet30PDU7 4 }

pf30PDU7 OBJECT-TYPE
SYNTAX INTEGER (0..65535)
ACCESS read-only
STATUS optional
DESCRIPTION
        " "
::= { outlet30PDU7 5 }

energy30PDU7 OBJECT-TYPE
SYNTAX INTEGER (0..65535)
ACCESS read-only
STATUS optional
DESCRIPTION
        " "
::= { outlet30PDU7 6 }

switch31PDU7 OBJECT-TYPE
SYNTAX INTEGER (0..3)
ACCESS read-write
STATUS optional
DESCRIPTION
        " "
::= { outlet31PDU7 1 }

voltage31PDU7 OBJECT-TYPE
SYNTAX INTEGER (0..65535)
ACCESS read-only
STATUS optional
DESCRIPTION
        " "
::= { outlet31PDU7 2 }

current31PDU7 OBJECT-TYPE
SYNTAX INTEGER (0..65535)
ACCESS read-only
STATUS optional
DESCRIPTION
        " "
::= { outlet31PDU7 3 }

power31PDU7 OBJECT-TYPE
SYNTAX INTEGER (0..65535)
ACCESS read-only
STATUS optional
DESCRIPTION
        " "
::= { outlet31PDU7 4 }

pf31PDU7 OBJECT-TYPE
SYNTAX INTEGER (0..65535)
ACCESS read-only
STATUS optional
DESCRIPTION
        " "
::= { outlet31PDU7 5 }

energy31PDU7 OBJECT-TYPE
SYNTAX INTEGER (0..65535)
ACCESS read-only
STATUS optional
DESCRIPTION
        " "
::= { outlet31PDU7 6 }

switch32PDU7 OBJECT-TYPE
SYNTAX INTEGER (0..3)
ACCESS read-write
STATUS optional
DESCRIPTION
        " "
::= { outlet32PDU7 1 }

voltage32PDU7 OBJECT-TYPE
SYNTAX INTEGER (0..65535)
ACCESS read-only
STATUS optional
DESCRIPTION
        " "
::= { outlet32PDU7 2 }

current32PDU7 OBJECT-TYPE
SYNTAX INTEGER (0..65535)
ACCESS read-only
STATUS optional
DESCRIPTION
        " "
::= { outlet32PDU7 3 }

power32PDU7 OBJECT-TYPE
SYNTAX INTEGER (0..65535)
ACCESS read-only
STATUS optional
DESCRIPTION
        " "
::= { outlet32PDU7 4 }

pf32PDU7 OBJECT-TYPE
SYNTAX INTEGER (0..65535)
ACCESS read-only
STATUS optional
DESCRIPTION
        " "
::= { outlet32PDU7 5 }

energy32PDU7 OBJECT-TYPE
SYNTAX INTEGER (0..65535)
ACCESS read-only
STATUS optional
DESCRIPTION
        " "
::= { outlet32PDU7 6 }

switch33PDU7 OBJECT-TYPE
SYNTAX INTEGER (0..3)
ACCESS read-write
STATUS optional
DESCRIPTION
        " "
::= { outlet33PDU7 1 }

voltage33PDU7 OBJECT-TYPE
SYNTAX INTEGER (0..65535)
ACCESS read-only
STATUS optional
DESCRIPTION
        " "
::= { outlet33PDU7 2 }

current33PDU7 OBJECT-TYPE
SYNTAX INTEGER (0..65535)
ACCESS read-only
STATUS optional
DESCRIPTION
        " "
::= { outlet33PDU7 3 }

power33PDU7 OBJECT-TYPE
SYNTAX INTEGER (0..65535)
ACCESS read-only
STATUS optional
DESCRIPTION
        " "
::= { outlet33PDU7 4 }

pf33PDU7 OBJECT-TYPE
SYNTAX INTEGER (0..65535)
ACCESS read-only
STATUS optional
DESCRIPTION
        " "
::= { outlet33PDU7 5 }

energy33PDU7 OBJECT-TYPE
SYNTAX INTEGER (0..65535)
ACCESS read-only
STATUS optional
DESCRIPTION
        " "
::= { outlet33PDU7 6 }

switch34PDU7 OBJECT-TYPE
SYNTAX INTEGER (0..3)
ACCESS read-write
STATUS optional
DESCRIPTION
        " "
::= { outlet34PDU7 1 }

voltage34PDU7 OBJECT-TYPE
SYNTAX INTEGER (0..65535)
ACCESS read-only
STATUS optional
DESCRIPTION
        " "
::= { outlet34PDU7 2 }

current34PDU7 OBJECT-TYPE
SYNTAX INTEGER (0..65535)
ACCESS read-only
STATUS optional
DESCRIPTION
        " "
::= { outlet34PDU7 3 }

power34PDU7 OBJECT-TYPE
SYNTAX INTEGER (0..65535)
ACCESS read-only
STATUS optional
DESCRIPTION
        " "
::= { outlet34PDU7 4 }

pf34PDU7 OBJECT-TYPE
SYNTAX INTEGER (0..65535)
ACCESS read-only
STATUS optional
DESCRIPTION
        " "
::= { outlet34PDU7 5 }

energy34PDU7 OBJECT-TYPE
SYNTAX INTEGER (0..65535)
ACCESS read-only
STATUS optional
DESCRIPTION
        " "
::= { outlet34PDU7 6 }

switch35PDU7 OBJECT-TYPE
SYNTAX INTEGER (0..3)
ACCESS read-write
STATUS optional
DESCRIPTION
        " "
::= { outlet35PDU7 1 }

voltage35PDU7 OBJECT-TYPE
SYNTAX INTEGER (0..65535)
ACCESS read-only
STATUS optional
DESCRIPTION
        " "
::= { outlet35PDU7 2 }

current35PDU7 OBJECT-TYPE
SYNTAX INTEGER (0..65535)
ACCESS read-only
STATUS optional
DESCRIPTION
        " "
::= { outlet35PDU7 3 }

power35PDU7 OBJECT-TYPE
SYNTAX INTEGER (0..65535)
ACCESS read-only
STATUS optional
DESCRIPTION
        " "
::= { outlet35PDU7 4 }

pf35PDU7 OBJECT-TYPE
SYNTAX INTEGER (0..65535)
ACCESS read-only
STATUS optional
DESCRIPTION
        " "
::= { outlet35PDU7 5 }

energy35PDU7 OBJECT-TYPE
SYNTAX INTEGER (0..65535)
ACCESS read-only
STATUS optional
DESCRIPTION
        " "
::= { outlet35PDU7 6 }

switch36PDU7 OBJECT-TYPE
SYNTAX INTEGER (0..3)
ACCESS read-write
STATUS optional
DESCRIPTION
        " "
::= { outlet36PDU7 1 }

voltage36PDU7 OBJECT-TYPE
SYNTAX INTEGER (0..65535)
ACCESS read-only
STATUS optional
DESCRIPTION
        " "
::= { outlet36PDU7 2 }

current36PDU7 OBJECT-TYPE
SYNTAX INTEGER (0..65535)
ACCESS read-only
STATUS optional
DESCRIPTION
        " "
::= { outlet36PDU7 3 }

power36PDU7 OBJECT-TYPE
SYNTAX INTEGER (0..65535)
ACCESS read-only
STATUS optional
DESCRIPTION
        " "
::= { outlet36PDU7 4 }

pf36PDU7 OBJECT-TYPE
SYNTAX INTEGER (0..65535)
ACCESS read-only
STATUS optional
DESCRIPTION
        " "
::= { outlet36PDU7 5 }

energy36PDU7 OBJECT-TYPE
SYNTAX INTEGER (0..65535)
ACCESS read-only
STATUS optional
DESCRIPTION
        " "
::= { outlet36PDU7 6 }

sensor1 OBJECT IDENTIFIER ::= { pdu7 4 }

temperature1PDU7 OBJECT-TYPE
SYNTAX INTEGER (0..65535)
ACCESS read-only
STATUS optional
DESCRIPTION
        " "
::= { sensor1 1 }

humidity1PDU7 OBJECT-TYPE
SYNTAX INTEGER (0..65535)
ACCESS read-only
STATUS optional
DESCRIPTION
        " "
::= { sensor1 2 }

temperature2PDU7 OBJECT-TYPE
SYNTAX INTEGER (0..65535)
ACCESS read-only
STATUS optional
DESCRIPTION
        " "
::= { sensor1 3 }

humidity2PDU7 OBJECT-TYPE
SYNTAX INTEGER (0..65535)
ACCESS read-only
STATUS optional
DESCRIPTION
        " "
::= { sensor1 4 }

inputStatus1PDU7 OBJECT-TYPE
SYNTAX INTEGER (0..1)
ACCESS read-only
STATUS optional
DESCRIPTION
        " "
::= { sensor1 5 }

inputStatus2PDU7 OBJECT-TYPE
SYNTAX INTEGER (0..1)
ACCESS read-only
STATUS optional
DESCRIPTION
        " "
::= { sensor1 6 }

inputStatus3PDU7 OBJECT-TYPE
SYNTAX INTEGER (0..1)
ACCESS read-only
STATUS optional
DESCRIPTION
        " "
::= { sensor1 7 }

inputStatus4PDU7 OBJECT-TYPE
SYNTAX INTEGER (0..1)
ACCESS read-only
STATUS optional
DESCRIPTION
        " "
::= { sensor1 8 }

doStatus1PDU7 OBJECT-TYPE
SYNTAX INTEGER (0..1)
ACCESS read-only
STATUS optional
DESCRIPTION
        " "
::= { sensor1 9 }

doStatus2PDU7 OBJECT-TYPE
SYNTAX INTEGER (0..1)
ACCESS read-only
STATUS optional
DESCRIPTION
        " "
::= { sensor1 10 }

baseinfo1 OBJECT IDENTIFIER ::= { pdu8 1 }

cascadeAlarmPDU8 OBJECT-TYPE
SYNTAX INTEGER (0..3)
ACCESS read-only
STATUS optional
DESCRIPTION
        " "
::= { baseinfo1 1 }

deviceNamePDU8 OBJECT-TYPE
SYNTAX DisplayString (SIZE (32))
ACCESS read-write
STATUS optional
DESCRIPTION
        " "
::= { baseinfo1 2 }

outletNumberPDU8 OBJECT-TYPE
SYNTAX INTEGER (0..36)
ACCESS read-only
STATUS optional
DESCRIPTION
        " "
::= { baseinfo1 3 }

temphum1WarnStatPDU8 OBJECT-TYPE
SYNTAX INTEGER (0..127)
ACCESS read-only
STATUS optional
DESCRIPTION
        " "
::= { baseinfo1 4 }

temphum2WarnStatPDU8 OBJECT-TYPE
SYNTAX INTEGER (0..127)
ACCESS read-only
STATUS optional
DESCRIPTION
        " "
::= { baseinfo1 5 }

input1WarnStatPDU8 OBJECT-TYPE
SYNTAX INTEGER (0..1)
ACCESS read-only
STATUS optional
DESCRIPTION
        " "
::= { baseinfo1 6 }

input2WarnStatPDU8 OBJECT-TYPE
SYNTAX INTEGER (0..1)
ACCESS read-only
STATUS optional
DESCRIPTION
        " "
::= { baseinfo1 7 }

input3WarnStatPDU8 OBJECT-TYPE
SYNTAX INTEGER (0..1)
ACCESS read-only
STATUS optional
DESCRIPTION
        " "
::= { baseinfo1 8 }

input4WarnStatPDU8 OBJECT-TYPE
SYNTAX INTEGER (0..1)
ACCESS read-only
STATUS optional
DESCRIPTION
        " "
::= { baseinfo1 9 }

currentL1WarnStatPDU8 OBJECT-TYPE
SYNTAX INTEGER (0..127)
ACCESS read-only
STATUS optional
DESCRIPTION
        " "
::= { baseinfo1 10 }

currentL2WarnStatPDU8 OBJECT-TYPE
SYNTAX INTEGER (0..127)
ACCESS read-only
STATUS optional
DESCRIPTION
        " "
::= { baseinfo1 11 }

currentL3WarnStatPDU8 OBJECT-TYPE
SYNTAX INTEGER (0..127)
ACCESS read-only
STATUS optional
DESCRIPTION
        " "
::= { baseinfo1 12 }

voltageL1WarnStatPDU8 OBJECT-TYPE
SYNTAX INTEGER (0..127)
ACCESS read-only
STATUS optional
DESCRIPTION
        " "
::= { baseinfo1 13 }

voltageL2WarnStatPDU8 OBJECT-TYPE
SYNTAX INTEGER (0..127)
ACCESS read-only
STATUS optional
DESCRIPTION
        " "
::= { baseinfo1 14 }

voltageL3WarnStatPDU8 OBJECT-TYPE
SYNTAX INTEGER (0..127)
ACCESS read-only
STATUS optional
DESCRIPTION
        " "
::= { baseinfo1 15 }

outlet1WarnStatPDU8 OBJECT-TYPE
SYNTAX INTEGER (0..127)
ACCESS read-only
STATUS optional
DESCRIPTION
        " "
::= { baseinfo1 16 }

outlet2WarnStatPDU8 OBJECT-TYPE
SYNTAX INTEGER (0..127)
ACCESS read-only
STATUS optional
DESCRIPTION
        " "
::= { baseinfo1 17 }

outlet3WarnStatPDU8 OBJECT-TYPE
SYNTAX INTEGER (0..127)
ACCESS read-only
STATUS optional
DESCRIPTION
        " "
::= { baseinfo1 18 }

outlet4WarnStatPDU8 OBJECT-TYPE
SYNTAX INTEGER (0..127)
ACCESS read-only
STATUS optional
DESCRIPTION
        " "
::= { baseinfo1 19 }

outlet5WarnStatPDU8 OBJECT-TYPE
SYNTAX INTEGER (0..127)
ACCESS read-only
STATUS optional
DESCRIPTION
        " "
::= { baseinfo1 20 }

outlet6WarnStatPDU8 OBJECT-TYPE
SYNTAX INTEGER (0..127)
ACCESS read-only
STATUS optional
DESCRIPTION
        " "
::= { baseinfo1 21 }

outlet7WarnStatPDU8 OBJECT-TYPE
SYNTAX INTEGER (0..127)
ACCESS read-only
STATUS optional
DESCRIPTION
        " "
::= { baseinfo1 22 }

outlet8WarnStatPDU8 OBJECT-TYPE
SYNTAX INTEGER (0..127)
ACCESS read-only
STATUS optional
DESCRIPTION
        " "
::= { baseinfo1 23 }

outlet9WarnStatPDU8 OBJECT-TYPE
SYNTAX INTEGER (0..127)
ACCESS read-only
STATUS optional
DESCRIPTION
        " "
::= { baseinfo1 24 }

outlet10WarnStatPDU8 OBJECT-TYPE
SYNTAX INTEGER (0..127)
ACCESS read-only
STATUS optional
DESCRIPTION
        " "
::= { baseinfo1 25 }

outlet11WarnStatPDU8 OBJECT-TYPE
SYNTAX INTEGER (0..127)
ACCESS read-only
STATUS optional
DESCRIPTION
        " "
::= { baseinfo1 26 }

outlet12WarnStatPDU8 OBJECT-TYPE
SYNTAX INTEGER (0..127)
ACCESS read-only
STATUS optional
DESCRIPTION
        " "
::= { baseinfo1 27 }

outlet13WarnStatPDU8 OBJECT-TYPE
SYNTAX INTEGER (0..127)
ACCESS read-only
STATUS optional
DESCRIPTION
        " "
::= { baseinfo1 28 }

outlet14WarnStatPDU8 OBJECT-TYPE
SYNTAX INTEGER (0..127)
ACCESS read-only
STATUS optional
DESCRIPTION
        " "
::= { baseinfo1 29 }

outlet15WarnStatPDU8 OBJECT-TYPE
SYNTAX INTEGER (0..127)
ACCESS read-only
STATUS optional
DESCRIPTION
        " "
::= { baseinfo1 30 }

outlet16WarnStatPDU8 OBJECT-TYPE
SYNTAX INTEGER (0..127)
ACCESS read-only
STATUS optional
DESCRIPTION
        " "
::= { baseinfo1 31 }

outlet17WarnStatPDU8 OBJECT-TYPE
SYNTAX INTEGER (0..127)
ACCESS read-only
STATUS optional
DESCRIPTION
        " "
::= { baseinfo1 32 }

outlet18WarnStatPDU8 OBJECT-TYPE
SYNTAX INTEGER (0..127)
ACCESS read-only
STATUS optional
DESCRIPTION
        " "
::= { baseinfo1 33 }

outlet19WarnStatPDU8 OBJECT-TYPE
SYNTAX INTEGER (0..127)
ACCESS read-only
STATUS optional
DESCRIPTION
        " "
::= { baseinfo1 34 }

outlet20WarnStatPDU8 OBJECT-TYPE
SYNTAX INTEGER (0..127)
ACCESS read-only
STATUS optional
DESCRIPTION
        " "
::= { baseinfo1 35 }

outlet21WarnStatPDU8 OBJECT-TYPE
SYNTAX INTEGER (0..127)
ACCESS read-only
STATUS optional
DESCRIPTION
        " "
::= { baseinfo1 36 }

outlet22WarnStatPDU8 OBJECT-TYPE
SYNTAX INTEGER (0..127)
ACCESS read-only
STATUS optional
DESCRIPTION
        " "
::= { baseinfo1 37 }

outlet23WarnStatPDU8 OBJECT-TYPE
SYNTAX INTEGER (0..127)
ACCESS read-only
STATUS optional
DESCRIPTION
        " "
::= { baseinfo1 38 }

outlet24WarnStatPDU8 OBJECT-TYPE
SYNTAX INTEGER (0..127)
ACCESS read-only
STATUS optional
DESCRIPTION
        " "
::= { baseinfo1 39 }

outlet25WarnStatPDU8 OBJECT-TYPE
SYNTAX INTEGER (0..127)
ACCESS read-only
STATUS optional
DESCRIPTION
        " "
::= { baseinfo1 40 }

outlet26WarnStatPDU8 OBJECT-TYPE
SYNTAX INTEGER (0..127)
ACCESS read-only
STATUS optional
DESCRIPTION
        " "
::= { baseinfo1 41 }

outlet27WarnStatPDU8 OBJECT-TYPE
SYNTAX INTEGER (0..127)
ACCESS read-only
STATUS optional
DESCRIPTION
        " "
::= { baseinfo1 42 }

outlet28WarnStatPDU8 OBJECT-TYPE
SYNTAX INTEGER (0..127)
ACCESS read-only
STATUS optional
DESCRIPTION
        " "
::= { baseinfo1 43 }

outlet29WarnStatPDU8 OBJECT-TYPE
SYNTAX INTEGER (0..127)
ACCESS read-only
STATUS optional
DESCRIPTION
        " "
::= { baseinfo1 44 }

outlet30WarnStatPDU8 OBJECT-TYPE
SYNTAX INTEGER (0..127)
ACCESS read-only
STATUS optional
DESCRIPTION
        " "
::= { baseinfo1 45 }

outlet31WarnStatPDU8 OBJECT-TYPE
SYNTAX INTEGER (0..127)
ACCESS read-only
STATUS optional
DESCRIPTION
        " "
::= { baseinfo1 46 }

outlet32WarnStatPDU8 OBJECT-TYPE
SYNTAX INTEGER (0..127)
ACCESS read-only
STATUS optional
DESCRIPTION
        " "
::= { baseinfo1 47 }

outlet33WarnStatPDU8 OBJECT-TYPE
SYNTAX INTEGER (0..127)
ACCESS read-only
STATUS optional
DESCRIPTION
        " "
::= { baseinfo1 48 }

outlet34WarnStatPDU8 OBJECT-TYPE
SYNTAX INTEGER (0..127)
ACCESS read-only
STATUS optional
DESCRIPTION
        " "
::= { baseinfo1 49 }

outlet35WarnStatPDU8 OBJECT-TYPE
SYNTAX INTEGER (0..127)
ACCESS read-only
STATUS optional
DESCRIPTION
        " "
::= { baseinfo1 50 }

outlet36WarnStatPDU8 OBJECT-TYPE
SYNTAX INTEGER (0..127)
ACCESS read-only
STATUS optional
DESCRIPTION
        " "
::= { baseinfo1 51 }

input1 OBJECT IDENTIFIER ::= { pdu8 2 }

currentL1PDU8 OBJECT-TYPE
SYNTAX INTEGER (0..65535)
ACCESS read-only
STATUS optional
DESCRIPTION
        " "
::= { input1 1 }

voltageL1PDU8 OBJECT-TYPE
SYNTAX INTEGER (0..65535)
ACCESS read-only
STATUS optional
DESCRIPTION
        " "
::= { input1 2 }

powerL1PDU8 OBJECT-TYPE
SYNTAX INTEGER (0..65535)
ACCESS read-only
STATUS optional
DESCRIPTION
        " "
::= { input1 3 }

pfL1PDU8 OBJECT-TYPE
SYNTAX INTEGER (0..65535)
ACCESS read-only
STATUS optional
DESCRIPTION
        " "
::= { input1 4 }

energyL1PDU8 OBJECT-TYPE
SYNTAX INTEGER (0..65535)
ACCESS read-only
STATUS optional
DESCRIPTION
        " "
::= { input1 5 }

currentL2PDU8 OBJECT-TYPE
SYNTAX INTEGER (0..65535)
ACCESS read-only
STATUS optional
DESCRIPTION
        " "
::= { input1 6 }

voltageL2PDU8 OBJECT-TYPE
SYNTAX INTEGER (0..65535)
ACCESS read-only
STATUS optional
DESCRIPTION
        " "
::= { input1 7 }

powerL2PDU8 OBJECT-TYPE
SYNTAX INTEGER (0..65535)
ACCESS read-only
STATUS optional
DESCRIPTION
        " "
::= { input1 8 }

pfL2PDU8 OBJECT-TYPE
SYNTAX INTEGER (0..65535)
ACCESS read-only
STATUS optional
DESCRIPTION
        " "
::= { input1 9 }

energyL2PDU8 OBJECT-TYPE
SYNTAX INTEGER (0..65535)
ACCESS read-only
STATUS optional
DESCRIPTION
        " "
::= { input1 10 }

currentL3PDU8 OBJECT-TYPE
SYNTAX INTEGER (0..65535)
ACCESS read-only
STATUS optional
DESCRIPTION
        " "
::= { input1 11 }

voltageL3PDU8 OBJECT-TYPE
SYNTAX INTEGER (0..65535)
ACCESS read-only
STATUS optional
DESCRIPTION
        " "
::= { input1 12 }

powerL3PDU8 OBJECT-TYPE
SYNTAX INTEGER (0..65535)
ACCESS read-only
STATUS optional
DESCRIPTION
        " "
::= { input1 13 }

pfL3PDU8 OBJECT-TYPE
SYNTAX INTEGER (0..65535)
ACCESS read-only
STATUS optional
DESCRIPTION
        " "
::= { input1 14 }

energyL3PDU8 OBJECT-TYPE
SYNTAX INTEGER (0..65535)
ACCESS read-only
STATUS optional
DESCRIPTION
        " "
::= { input1 15 }

outletinfo1 OBJECT IDENTIFIER ::= { pdu8 3 }

outlet1PDU8 OBJECT IDENTIFIER ::= { outletinfo1 1 }

outlet2PDU8 OBJECT IDENTIFIER ::= { outletinfo1 2 }

outlet3PDU8 OBJECT IDENTIFIER ::= { outletinfo1 3 }

outlet4PDU8 OBJECT IDENTIFIER ::= { outletinfo1 4 }

outlet5PDU8 OBJECT IDENTIFIER ::= { outletinfo1 5 }

outlet6PDU8 OBJECT IDENTIFIER ::= { outletinfo1 6 }

outlet7PDU8 OBJECT IDENTIFIER ::= { outletinfo1 7 }

outlet8PDU8 OBJECT IDENTIFIER ::= { outletinfo1 8 }

outlet9PDU8 OBJECT IDENTIFIER ::= { outletinfo1 9 }

outlet10PDU8 OBJECT IDENTIFIER ::= { outletinfo1 10 }

outlet11PDU8 OBJECT IDENTIFIER ::= { outletinfo1 11 }

outlet12PDU8 OBJECT IDENTIFIER ::= { outletinfo1 12 }

outlet13PDU8 OBJECT IDENTIFIER ::= { outletinfo1 13 }

outlet14PDU8 OBJECT IDENTIFIER ::= { outletinfo1 14 }

outlet15PDU8 OBJECT IDENTIFIER ::= { outletinfo1 15 }

outlet16PDU8 OBJECT IDENTIFIER ::= { outletinfo1 16 }

outlet17PDU8 OBJECT IDENTIFIER ::= { outletinfo1 17 }

outlet18PDU8 OBJECT IDENTIFIER ::= { outletinfo1 18 }

outlet19PDU8 OBJECT IDENTIFIER ::= { outletinfo1 19 }

outlet20PDU8 OBJECT IDENTIFIER ::= { outletinfo1 20 }

outlet21PDU8 OBJECT IDENTIFIER ::= { outletinfo1 21 }

outlet22PDU8 OBJECT IDENTIFIER ::= { outletinfo1 22 }

outlet23PDU8 OBJECT IDENTIFIER ::= { outletinfo1 23 }

outlet24PDU8 OBJECT IDENTIFIER ::= { outletinfo1 24 }

outlet25PDU8 OBJECT IDENTIFIER ::= { outletinfo1 25 }

outlet26PDU8 OBJECT IDENTIFIER ::= { outletinfo1 26 }

outlet27PDU8 OBJECT IDENTIFIER ::= { outletinfo1 27 }

outlet28PDU8 OBJECT IDENTIFIER ::= { outletinfo1 28 }

outlet29PDU8 OBJECT IDENTIFIER ::= { outletinfo1 29 }

outlet30PDU8 OBJECT IDENTIFIER ::= { outletinfo1 30 }

outlet31PDU8 OBJECT IDENTIFIER ::= { outletinfo1 31 }

outlet32PDU8 OBJECT IDENTIFIER ::= { outletinfo1 32 }

outlet33PDU8 OBJECT IDENTIFIER ::= { outletinfo1 33 }

outlet34PDU8 OBJECT IDENTIFIER ::= { outletinfo1 34 }

outlet35PDU8 OBJECT IDENTIFIER ::= { outletinfo1 35 }

outlet36PDU8 OBJECT IDENTIFIER ::= { outletinfo1 36 }

switch1PDU8 OBJECT-TYPE
SYNTAX INTEGER (0..3)
ACCESS read-write
STATUS optional
DESCRIPTION
        " "
::= { outlet1PDU8 1 }

voltage1PDU8 OBJECT-TYPE
SYNTAX INTEGER (0..65535)
ACCESS read-only
STATUS optional
DESCRIPTION
        " "
::= { outlet1PDU8 2 }

current1PDU8 OBJECT-TYPE
SYNTAX INTEGER (0..65535)
ACCESS read-only
STATUS optional
DESCRIPTION
        " "
::= { outlet1PDU8 3 }

power1PDU8 OBJECT-TYPE
SYNTAX INTEGER (0..65535)
ACCESS read-only
STATUS optional
DESCRIPTION
        " "
::= { outlet1PDU8 4 }

pf1PDU8 OBJECT-TYPE
SYNTAX INTEGER (0..65535)
ACCESS read-only
STATUS optional
DESCRIPTION
        " "
::= { outlet1PDU8 5 }

energy1PDU8 OBJECT-TYPE
SYNTAX INTEGER (0..65535)
ACCESS read-only
STATUS optional
DESCRIPTION
        " "
::= { outlet1PDU8 6 }

switch2PDU8 OBJECT-TYPE
SYNTAX INTEGER (0..3)
ACCESS read-write
STATUS optional
DESCRIPTION
        " "
::= { outlet2PDU8 1 }

voltage2PDU8 OBJECT-TYPE
SYNTAX INTEGER (0..65535)
ACCESS read-only
STATUS optional
DESCRIPTION
        " "
::= { outlet2PDU8 2 }

current2PDU8 OBJECT-TYPE
SYNTAX INTEGER (0..65535)
ACCESS read-only
STATUS optional
DESCRIPTION
        " "
::= { outlet2PDU8 3 }

power2PDU8 OBJECT-TYPE
SYNTAX INTEGER (0..65535)
ACCESS read-only
STATUS optional
DESCRIPTION
        " "
::= { outlet2PDU8 4 }

pf2PDU8 OBJECT-TYPE
SYNTAX INTEGER (0..65535)
ACCESS read-only
STATUS optional
DESCRIPTION
        " "
::= { outlet2PDU8 5 }

energy2PDU8 OBJECT-TYPE
SYNTAX INTEGER (0..65535)
ACCESS read-only
STATUS optional
DESCRIPTION
        " "
::= { outlet2PDU8 6 }

switch3PDU8 OBJECT-TYPE
SYNTAX INTEGER (0..3)
ACCESS read-write
STATUS optional
DESCRIPTION
        " "
::= { outlet3PDU8 1 }

voltage3PDU8 OBJECT-TYPE
SYNTAX INTEGER (0..65535)
ACCESS read-only
STATUS optional
DESCRIPTION
        " "
::= { outlet3PDU8 2 }

current3PDU8 OBJECT-TYPE
SYNTAX INTEGER (0..65535)
ACCESS read-only
STATUS optional
DESCRIPTION
        " "
::= { outlet3PDU8 3 }

power3PDU8 OBJECT-TYPE
SYNTAX INTEGER (0..65535)
ACCESS read-only
STATUS optional
DESCRIPTION
        " "
::= { outlet3PDU8 4 }

pf3PDU8 OBJECT-TYPE
SYNTAX INTEGER (0..65535)
ACCESS read-only
STATUS optional
DESCRIPTION
        " "
::= { outlet3PDU8 5 }

energy3PDU8 OBJECT-TYPE
SYNTAX INTEGER (0..65535)
ACCESS read-only
STATUS optional
DESCRIPTION
        " "
::= { outlet3PDU8 6 }

switch4PDU8 OBJECT-TYPE
SYNTAX INTEGER (0..3)
ACCESS read-write
STATUS optional
DESCRIPTION
        " "
::= { outlet4PDU8 1 }

voltage4PDU8 OBJECT-TYPE
SYNTAX INTEGER (0..65535)
ACCESS read-only
STATUS optional
DESCRIPTION
        " "
::= { outlet4PDU8 2 }

current4PDU8 OBJECT-TYPE
SYNTAX INTEGER (0..65535)
ACCESS read-only
STATUS optional
DESCRIPTION
        " "
::= { outlet4PDU8 3 }

power4PDU8 OBJECT-TYPE
SYNTAX INTEGER (0..65535)
ACCESS read-only
STATUS optional
DESCRIPTION
        " "
::= { outlet4PDU8 4 }

pf4PDU8 OBJECT-TYPE
SYNTAX INTEGER (0..65535)
ACCESS read-only
STATUS optional
DESCRIPTION
        " "
::= { outlet4PDU8 5 }

energy4PDU8 OBJECT-TYPE
SYNTAX INTEGER (0..65535)
ACCESS read-only
STATUS optional
DESCRIPTION
        " "
::= { outlet4PDU8 6 }

switch5PDU8 OBJECT-TYPE
SYNTAX INTEGER (0..3)
ACCESS read-write
STATUS optional
DESCRIPTION
        " "
::= { outlet5PDU8 1 }

voltage5PDU8 OBJECT-TYPE
SYNTAX INTEGER (0..65535)
ACCESS read-only
STATUS optional
DESCRIPTION
        " "
::= { outlet5PDU8 2 }

current5PDU8 OBJECT-TYPE
SYNTAX INTEGER (0..65535)
ACCESS read-only
STATUS optional
DESCRIPTION
        " "
::= { outlet5PDU8 3 }

power5PDU8 OBJECT-TYPE
SYNTAX INTEGER (0..65535)
ACCESS read-only
STATUS optional
DESCRIPTION
        " "
::= { outlet5PDU8 4 }

pf5PDU8 OBJECT-TYPE
SYNTAX INTEGER (0..65535)
ACCESS read-only
STATUS optional
DESCRIPTION
        " "
::= { outlet5PDU8 5 }

energy5PDU8 OBJECT-TYPE
SYNTAX INTEGER (0..65535)
ACCESS read-only
STATUS optional
DESCRIPTION
        " "
::= { outlet5PDU8 6 }

switch6PDU8 OBJECT-TYPE
SYNTAX INTEGER (0..3)
ACCESS read-write
STATUS optional
DESCRIPTION
        " "
::= { outlet6PDU8 1 }

voltage6PDU8 OBJECT-TYPE
SYNTAX INTEGER (0..65535)
ACCESS read-only
STATUS optional
DESCRIPTION
        " "
::= { outlet6PDU8 2 }

current6PDU8 OBJECT-TYPE
SYNTAX INTEGER (0..65535)
ACCESS read-only
STATUS optional
DESCRIPTION
        " "
::= { outlet6PDU8 3 }

power6PDU8 OBJECT-TYPE
SYNTAX INTEGER (0..65535)
ACCESS read-only
STATUS optional
DESCRIPTION
        " "
::= { outlet6PDU8 4 }

pf6PDU8 OBJECT-TYPE
SYNTAX INTEGER (0..65535)
ACCESS read-only
STATUS optional
DESCRIPTION
        " "
::= { outlet6PDU8 5 }

energy6PDU8 OBJECT-TYPE
SYNTAX INTEGER (0..65535)
ACCESS read-only
STATUS optional
DESCRIPTION
        " "
::= { outlet6PDU8 6 }

switch7PDU8 OBJECT-TYPE
SYNTAX INTEGER (0..3)
ACCESS read-write
STATUS optional
DESCRIPTION
        " "
::= { outlet7PDU8 1 }

voltage7PDU8 OBJECT-TYPE
SYNTAX INTEGER (0..65535)
ACCESS read-only
STATUS optional
DESCRIPTION
        " "
::= { outlet7PDU8 2 }

current7PDU8 OBJECT-TYPE
SYNTAX INTEGER (0..65535)
ACCESS read-only
STATUS optional
DESCRIPTION
        " "
::= { outlet7PDU8 3 }

power7PDU8 OBJECT-TYPE
SYNTAX INTEGER (0..65535)
ACCESS read-only
STATUS optional
DESCRIPTION
        " "
::= { outlet7PDU8 4 }

pf7PDU8 OBJECT-TYPE
SYNTAX INTEGER (0..65535)
ACCESS read-only
STATUS optional
DESCRIPTION
        " "
::= { outlet7PDU8 5 }

energy7PDU8 OBJECT-TYPE
SYNTAX INTEGER (0..65535)
ACCESS read-only
STATUS optional
DESCRIPTION
        " "
::= { outlet7PDU8 6 }

switch8PDU8 OBJECT-TYPE
SYNTAX INTEGER (0..3)
ACCESS read-write
STATUS optional
DESCRIPTION
        " "
::= { outlet8PDU8 1 }

voltage8PDU8 OBJECT-TYPE
SYNTAX INTEGER (0..65535)
ACCESS read-only
STATUS optional
DESCRIPTION
        " "
::= { outlet8PDU8 2 }

current8PDU8 OBJECT-TYPE
SYNTAX INTEGER (0..65535)
ACCESS read-only
STATUS optional
DESCRIPTION
        " "
::= { outlet8PDU8 3 }

power8PDU8 OBJECT-TYPE
SYNTAX INTEGER (0..65535)
ACCESS read-only
STATUS optional
DESCRIPTION
        " "
::= { outlet8PDU8 4 }

pf8PDU8 OBJECT-TYPE
SYNTAX INTEGER (0..65535)
ACCESS read-only
STATUS optional
DESCRIPTION
        " "
::= { outlet8PDU8 5 }

energy8PDU8 OBJECT-TYPE
SYNTAX INTEGER (0..65535)
ACCESS read-only
STATUS optional
DESCRIPTION
        " "
::= { outlet8PDU8 6 }

switch9PDU8 OBJECT-TYPE
SYNTAX INTEGER (0..3)
ACCESS read-write
STATUS optional
DESCRIPTION
        " "
::= { outlet9PDU8 1 }

voltage9PDU8 OBJECT-TYPE
SYNTAX INTEGER (0..65535)
ACCESS read-only
STATUS optional
DESCRIPTION
        " "
::= { outlet9PDU8 2 }

current9PDU8 OBJECT-TYPE
SYNTAX INTEGER (0..65535)
ACCESS read-only
STATUS optional
DESCRIPTION
        " "
::= { outlet9PDU8 3 }

power9PDU8 OBJECT-TYPE
SYNTAX INTEGER (0..65535)
ACCESS read-only
STATUS optional
DESCRIPTION
        " "
::= { outlet9PDU8 4 }

pf9PDU8 OBJECT-TYPE
SYNTAX INTEGER (0..65535)
ACCESS read-only
STATUS optional
DESCRIPTION
        " "
::= { outlet9PDU8 5 }

energy9PDU8 OBJECT-TYPE
SYNTAX INTEGER (0..65535)
ACCESS read-only
STATUS optional
DESCRIPTION
        " "
::= { outlet9PDU8 6 }

switch10PDU8 OBJECT-TYPE
SYNTAX INTEGER (0..3)
ACCESS read-write
STATUS optional
DESCRIPTION
        " "
::= { outlet10PDU8 1 }

voltage10PDU8 OBJECT-TYPE
SYNTAX INTEGER (0..65535)
ACCESS read-only
STATUS optional
DESCRIPTION
        " "
::= { outlet10PDU8 2 }

current10PDU8 OBJECT-TYPE
SYNTAX INTEGER (0..65535)
ACCESS read-only
STATUS optional
DESCRIPTION
        " "
::= { outlet10PDU8 3 }

power10PDU8 OBJECT-TYPE
SYNTAX INTEGER (0..65535)
ACCESS read-only
STATUS optional
DESCRIPTION
        " "
::= { outlet10PDU8 4 }

pf10PDU8 OBJECT-TYPE
SYNTAX INTEGER (0..65535)
ACCESS read-only
STATUS optional
DESCRIPTION
        " "
::= { outlet10PDU8 5 }

energy10PDU8 OBJECT-TYPE
SYNTAX INTEGER (0..65535)
ACCESS read-only
STATUS optional
DESCRIPTION
        " "
::= { outlet10PDU8 6 }

switch11PDU8 OBJECT-TYPE
SYNTAX INTEGER (0..3)
ACCESS read-write
STATUS optional
DESCRIPTION
        " "
::= { outlet11PDU8 1 }

voltage11PDU8 OBJECT-TYPE
SYNTAX INTEGER (0..65535)
ACCESS read-only
STATUS optional
DESCRIPTION
        " "
::= { outlet11PDU8 2 }

current11PDU8 OBJECT-TYPE
SYNTAX INTEGER (0..65535)
ACCESS read-only
STATUS optional
DESCRIPTION
        " "
::= { outlet11PDU8 3 }

power11PDU8 OBJECT-TYPE
SYNTAX INTEGER (0..65535)
ACCESS read-only
STATUS optional
DESCRIPTION
        " "
::= { outlet11PDU8 4 }

pf11PDU8 OBJECT-TYPE
SYNTAX INTEGER (0..65535)
ACCESS read-only
STATUS optional
DESCRIPTION
        " "
::= { outlet11PDU8 5 }

energy11PDU8 OBJECT-TYPE
SYNTAX INTEGER (0..65535)
ACCESS read-only
STATUS optional
DESCRIPTION
        " "
::= { outlet11PDU8 6 }

switch12PDU8 OBJECT-TYPE
SYNTAX INTEGER (0..3)
ACCESS read-write
STATUS optional
DESCRIPTION
        " "
::= { outlet12PDU8 1 }

voltage12PDU8 OBJECT-TYPE
SYNTAX INTEGER (0..65535)
ACCESS read-only
STATUS optional
DESCRIPTION
        " "
::= { outlet12PDU8 2 }

current12PDU8 OBJECT-TYPE
SYNTAX INTEGER (0..65535)
ACCESS read-only
STATUS optional
DESCRIPTION
        " "
::= { outlet12PDU8 3 }

power12PDU8 OBJECT-TYPE
SYNTAX INTEGER (0..65535)
ACCESS read-only
STATUS optional
DESCRIPTION
        " "
::= { outlet12PDU8 4 }

pf12PDU8 OBJECT-TYPE
SYNTAX INTEGER (0..65535)
ACCESS read-only
STATUS optional
DESCRIPTION
        " "
::= { outlet12PDU8 5 }

energy12PDU8 OBJECT-TYPE
SYNTAX INTEGER (0..65535)
ACCESS read-only
STATUS optional
DESCRIPTION
        " "
::= { outlet12PDU8 6 }

switch13PDU8 OBJECT-TYPE
SYNTAX INTEGER (0..3)
ACCESS read-write
STATUS optional
DESCRIPTION
        " "
::= { outlet13PDU8 1 }

voltage13PDU8 OBJECT-TYPE
SYNTAX INTEGER (0..65535)
ACCESS read-only
STATUS optional
DESCRIPTION
        " "
::= { outlet13PDU8 2 }

current13PDU8 OBJECT-TYPE
SYNTAX INTEGER (0..65535)
ACCESS read-only
STATUS optional
DESCRIPTION
        " "
::= { outlet13PDU8 3 }

power13PDU8 OBJECT-TYPE
SYNTAX INTEGER (0..65535)
ACCESS read-only
STATUS optional
DESCRIPTION
        " "
::= { outlet13PDU8 4 }

pf13PDU8 OBJECT-TYPE
SYNTAX INTEGER (0..65535)
ACCESS read-only
STATUS optional
DESCRIPTION
        " "
::= { outlet13PDU8 5 }

energy13PDU8 OBJECT-TYPE
SYNTAX INTEGER (0..65535)
ACCESS read-only
STATUS optional
DESCRIPTION
        " "
::= { outlet13PDU8 6 }

switch14PDU8 OBJECT-TYPE
SYNTAX INTEGER (0..3)
ACCESS read-write
STATUS optional
DESCRIPTION
        " "
::= { outlet14PDU8 1 }

voltage14PDU8 OBJECT-TYPE
SYNTAX INTEGER (0..65535)
ACCESS read-only
STATUS optional
DESCRIPTION
        " "
::= { outlet14PDU8 2 }

current14PDU8 OBJECT-TYPE
SYNTAX INTEGER (0..65535)
ACCESS read-only
STATUS optional
DESCRIPTION
        " "
::= { outlet14PDU8 3 }

power14PDU8 OBJECT-TYPE
SYNTAX INTEGER (0..65535)
ACCESS read-only
STATUS optional
DESCRIPTION
        " "
::= { outlet14PDU8 4 }

pf14PDU8 OBJECT-TYPE
SYNTAX INTEGER (0..65535)
ACCESS read-only
STATUS optional
DESCRIPTION
        " "
::= { outlet14PDU8 5 }

energy14PDU8 OBJECT-TYPE
SYNTAX INTEGER (0..65535)
ACCESS read-only
STATUS optional
DESCRIPTION
        " "
::= { outlet14PDU8 6 }

switch15PDU8 OBJECT-TYPE
SYNTAX INTEGER (0..3)
ACCESS read-write
STATUS optional
DESCRIPTION
        " "
::= { outlet15PDU8 1 }

voltage15PDU8 OBJECT-TYPE
SYNTAX INTEGER (0..65535)
ACCESS read-only
STATUS optional
DESCRIPTION
        " "
::= { outlet15PDU8 2 }

current15PDU8 OBJECT-TYPE
SYNTAX INTEGER (0..65535)
ACCESS read-only
STATUS optional
DESCRIPTION
        " "
::= { outlet15PDU8 3 }

power15PDU8 OBJECT-TYPE
SYNTAX INTEGER (0..65535)
ACCESS read-only
STATUS optional
DESCRIPTION
        " "
::= { outlet15PDU8 4 }

pf15PDU8 OBJECT-TYPE
SYNTAX INTEGER (0..65535)
ACCESS read-only
STATUS optional
DESCRIPTION
        " "
::= { outlet15PDU8 5 }

energy15PDU8 OBJECT-TYPE
SYNTAX INTEGER (0..65535)
ACCESS read-only
STATUS optional
DESCRIPTION
        " "
::= { outlet15PDU8 6 }

switch16PDU8 OBJECT-TYPE
SYNTAX INTEGER (0..3)
ACCESS read-write
STATUS optional
DESCRIPTION
        " "
::= { outlet16PDU8 1 }

voltage16PDU8 OBJECT-TYPE
SYNTAX INTEGER (0..65535)
ACCESS read-only
STATUS optional
DESCRIPTION
        " "
::= { outlet16PDU8 2 }

current16PDU8 OBJECT-TYPE
SYNTAX INTEGER (0..65535)
ACCESS read-only
STATUS optional
DESCRIPTION
        " "
::= { outlet16PDU8 3 }

power16PDU8 OBJECT-TYPE
SYNTAX INTEGER (0..65535)
ACCESS read-only
STATUS optional
DESCRIPTION
        " "
::= { outlet16PDU8 4 }

pf16PDU8 OBJECT-TYPE
SYNTAX INTEGER (0..65535)
ACCESS read-only
STATUS optional
DESCRIPTION
        " "
::= { outlet16PDU8 5 }

energy16PDU8 OBJECT-TYPE
SYNTAX INTEGER (0..65535)
ACCESS read-only
STATUS optional
DESCRIPTION
        " "
::= { outlet16PDU8 6 }

switch17PDU8 OBJECT-TYPE
SYNTAX INTEGER (0..3)
ACCESS read-write
STATUS optional
DESCRIPTION
        " "
::= { outlet17PDU8 1 }

voltage17PDU8 OBJECT-TYPE
SYNTAX INTEGER (0..65535)
ACCESS read-only
STATUS optional
DESCRIPTION
        " "
::= { outlet17PDU8 2 }

current17PDU8 OBJECT-TYPE
SYNTAX INTEGER (0..65535)
ACCESS read-only
STATUS optional
DESCRIPTION
        " "
::= { outlet17PDU8 3 }

power17PDU8 OBJECT-TYPE
SYNTAX INTEGER (0..65535)
ACCESS read-only
STATUS optional
DESCRIPTION
        " "
::= { outlet17PDU8 4 }

pf17PDU8 OBJECT-TYPE
SYNTAX INTEGER (0..65535)
ACCESS read-only
STATUS optional
DESCRIPTION
        " "
::= { outlet17PDU8 5 }

energy17PDU8 OBJECT-TYPE
SYNTAX INTEGER (0..65535)
ACCESS read-only
STATUS optional
DESCRIPTION
        " "
::= { outlet17PDU8 6 }

switch18PDU8 OBJECT-TYPE
SYNTAX INTEGER (0..3)
ACCESS read-write
STATUS optional
DESCRIPTION
        " "
::= { outlet18PDU8 1 }

voltage18PDU8 OBJECT-TYPE
SYNTAX INTEGER (0..65535)
ACCESS read-only
STATUS optional
DESCRIPTION
        " "
::= { outlet18PDU8 2 }

current18PDU8 OBJECT-TYPE
SYNTAX INTEGER (0..65535)
ACCESS read-only
STATUS optional
DESCRIPTION
        " "
::= { outlet18PDU8 3 }

power18PDU8 OBJECT-TYPE
SYNTAX INTEGER (0..65535)
ACCESS read-only
STATUS optional
DESCRIPTION
        " "
::= { outlet18PDU8 4 }

pf18PDU8 OBJECT-TYPE
SYNTAX INTEGER (0..65535)
ACCESS read-only
STATUS optional
DESCRIPTION
        " "
::= { outlet18PDU8 5 }

energy18PDU8 OBJECT-TYPE
SYNTAX INTEGER (0..65535)
ACCESS read-only
STATUS optional
DESCRIPTION
        " "
::= { outlet18PDU8 6 }

switch19PDU8 OBJECT-TYPE
SYNTAX INTEGER (0..3)
ACCESS read-write
STATUS optional
DESCRIPTION
        " "
::= { outlet19PDU8 1 }

voltage19PDU8 OBJECT-TYPE
SYNTAX INTEGER (0..65535)
ACCESS read-only
STATUS optional
DESCRIPTION
        " "
::= { outlet19PDU8 2 }

current19PDU8 OBJECT-TYPE
SYNTAX INTEGER (0..65535)
ACCESS read-only
STATUS optional
DESCRIPTION
        " "
::= { outlet19PDU8 3 }

power19PDU8 OBJECT-TYPE
SYNTAX INTEGER (0..65535)
ACCESS read-only
STATUS optional
DESCRIPTION
        " "
::= { outlet19PDU8 4 }

pf19PDU8 OBJECT-TYPE
SYNTAX INTEGER (0..65535)
ACCESS read-only
STATUS optional
DESCRIPTION
        " "
::= { outlet19PDU8 5 }

energy19PDU8 OBJECT-TYPE
SYNTAX INTEGER (0..65535)
ACCESS read-only
STATUS optional
DESCRIPTION
        " "
::= { outlet19PDU8 6 }

switch20PDU8 OBJECT-TYPE
SYNTAX INTEGER (0..3)
ACCESS read-write
STATUS optional
DESCRIPTION
        " "
::= { outlet20PDU8 1 }

voltage20PDU8 OBJECT-TYPE
SYNTAX INTEGER (0..65535)
ACCESS read-only
STATUS optional
DESCRIPTION
        " "
::= { outlet20PDU8 2 }

current20PDU8 OBJECT-TYPE
SYNTAX INTEGER (0..65535)
ACCESS read-only
STATUS optional
DESCRIPTION
        " "
::= { outlet20PDU8 3 }

power20PDU8 OBJECT-TYPE
SYNTAX INTEGER (0..65535)
ACCESS read-only
STATUS optional
DESCRIPTION
        " "
::= { outlet20PDU8 4 }

pf20PDU8 OBJECT-TYPE
SYNTAX INTEGER (0..65535)
ACCESS read-only
STATUS optional
DESCRIPTION
        " "
::= { outlet20PDU8 5 }

energy20PDU8 OBJECT-TYPE
SYNTAX INTEGER (0..65535)
ACCESS read-only
STATUS optional
DESCRIPTION
        " "
::= { outlet20PDU8 6 }

switch21PDU8 OBJECT-TYPE
SYNTAX INTEGER (0..3)
ACCESS read-write
STATUS optional
DESCRIPTION
        " "
::= { outlet21PDU8 1 }

voltage21PDU8 OBJECT-TYPE
SYNTAX INTEGER (0..65535)
ACCESS read-only
STATUS optional
DESCRIPTION
        " "
::= { outlet21PDU8 2 }

current21PDU8 OBJECT-TYPE
SYNTAX INTEGER (0..65535)
ACCESS read-only
STATUS optional
DESCRIPTION
        " "
::= { outlet21PDU8 3 }

power21PDU8 OBJECT-TYPE
SYNTAX INTEGER (0..65535)
ACCESS read-only
STATUS optional
DESCRIPTION
        " "
::= { outlet21PDU8 4 }

pf21PDU8 OBJECT-TYPE
SYNTAX INTEGER (0..65535)
ACCESS read-only
STATUS optional
DESCRIPTION
        " "
::= { outlet21PDU8 5 }

energy21PDU8 OBJECT-TYPE
SYNTAX INTEGER (0..65535)
ACCESS read-only
STATUS optional
DESCRIPTION
        " "
::= { outlet21PDU8 6 }

switch22PDU8 OBJECT-TYPE
SYNTAX INTEGER (0..3)
ACCESS read-write
STATUS optional
DESCRIPTION
        " "
::= { outlet22PDU8 1 }

voltage22PDU8 OBJECT-TYPE
SYNTAX INTEGER (0..65535)
ACCESS read-only
STATUS optional
DESCRIPTION
        " "
::= { outlet22PDU8 2 }

current22PDU8 OBJECT-TYPE
SYNTAX INTEGER (0..65535)
ACCESS read-only
STATUS optional
DESCRIPTION
        " "
::= { outlet22PDU8 3 }

power22PDU8 OBJECT-TYPE
SYNTAX INTEGER (0..65535)
ACCESS read-only
STATUS optional
DESCRIPTION
        " "
::= { outlet22PDU8 4 }

pf22PDU8 OBJECT-TYPE
SYNTAX INTEGER (0..65535)
ACCESS read-only
STATUS optional
DESCRIPTION
        " "
::= { outlet22PDU8 5 }

energy22PDU8 OBJECT-TYPE
SYNTAX INTEGER (0..65535)
ACCESS read-only
STATUS optional
DESCRIPTION
        " "
::= { outlet22PDU8 6 }

switch23PDU8 OBJECT-TYPE
SYNTAX INTEGER (0..3)
ACCESS read-write
STATUS optional
DESCRIPTION
        " "
::= { outlet23PDU8 1 }

voltage23PDU8 OBJECT-TYPE
SYNTAX INTEGER (0..65535)
ACCESS read-only
STATUS optional
DESCRIPTION
        " "
::= { outlet23PDU8 2 }

current23PDU8 OBJECT-TYPE
SYNTAX INTEGER (0..65535)
ACCESS read-only
STATUS optional
DESCRIPTION
        " "
::= { outlet23PDU8 3 }

power23PDU8 OBJECT-TYPE
SYNTAX INTEGER (0..65535)
ACCESS read-only
STATUS optional
DESCRIPTION
        " "
::= { outlet23PDU8 4 }

pf23PDU8 OBJECT-TYPE
SYNTAX INTEGER (0..65535)
ACCESS read-only
STATUS optional
DESCRIPTION
        " "
::= { outlet23PDU8 5 }

energy23PDU8 OBJECT-TYPE
SYNTAX INTEGER (0..65535)
ACCESS read-only
STATUS optional
DESCRIPTION
        " "
::= { outlet23PDU8 6 }

switch24PDU8 OBJECT-TYPE
SYNTAX INTEGER (0..3)
ACCESS read-write
STATUS optional
DESCRIPTION
        " "
::= { outlet24PDU8 1 }

voltage24PDU8 OBJECT-TYPE
SYNTAX INTEGER (0..65535)
ACCESS read-only
STATUS optional
DESCRIPTION
        " "
::= { outlet24PDU8 2 }

current24PDU8 OBJECT-TYPE
SYNTAX INTEGER (0..65535)
ACCESS read-only
STATUS optional
DESCRIPTION
        " "
::= { outlet24PDU8 3 }

power24PDU8 OBJECT-TYPE
SYNTAX INTEGER (0..65535)
ACCESS read-only
STATUS optional
DESCRIPTION
        " "
::= { outlet24PDU8 4 }

pf24PDU8 OBJECT-TYPE
SYNTAX INTEGER (0..65535)
ACCESS read-only
STATUS optional
DESCRIPTION
        " "
::= { outlet24PDU8 5 }

energy24PDU8 OBJECT-TYPE
SYNTAX INTEGER (0..65535)
ACCESS read-only
STATUS optional
DESCRIPTION
        " "
::= { outlet24PDU8 6 }

switch25PDU8 OBJECT-TYPE
SYNTAX INTEGER (0..3)
ACCESS read-write
STATUS optional
DESCRIPTION
        " "
::= { outlet25PDU8 1 }

voltage25PDU8 OBJECT-TYPE
SYNTAX INTEGER (0..65535)
ACCESS read-only
STATUS optional
DESCRIPTION
        " "
::= { outlet25PDU8 2 }

current25PDU8 OBJECT-TYPE
SYNTAX INTEGER (0..65535)
ACCESS read-only
STATUS optional
DESCRIPTION
        " "
::= { outlet25PDU8 3 }

power25PDU8 OBJECT-TYPE
SYNTAX INTEGER (0..65535)
ACCESS read-only
STATUS optional
DESCRIPTION
        " "
::= { outlet25PDU8 4 }

pf25PDU8 OBJECT-TYPE
SYNTAX INTEGER (0..65535)
ACCESS read-only
STATUS optional
DESCRIPTION
        " "
::= { outlet25PDU8 5 }

energy25PDU8 OBJECT-TYPE
SYNTAX INTEGER (0..65535)
ACCESS read-only
STATUS optional
DESCRIPTION
        " "
::= { outlet25PDU8 6 }

switch26PDU8 OBJECT-TYPE
SYNTAX INTEGER (0..3)
ACCESS read-write
STATUS optional
DESCRIPTION
        " "
::= { outlet26PDU8 1 }

voltage26PDU8 OBJECT-TYPE
SYNTAX INTEGER (0..65535)
ACCESS read-only
STATUS optional
DESCRIPTION
        " "
::= { outlet26PDU8 2 }

current26PDU8 OBJECT-TYPE
SYNTAX INTEGER (0..65535)
ACCESS read-only
STATUS optional
DESCRIPTION
        " "
::= { outlet26PDU8 3 }

power26PDU8 OBJECT-TYPE
SYNTAX INTEGER (0..65535)
ACCESS read-only
STATUS optional
DESCRIPTION
        " "
::= { outlet26PDU8 4 }

pf26PDU8 OBJECT-TYPE
SYNTAX INTEGER (0..65535)
ACCESS read-only
STATUS optional
DESCRIPTION
        " "
::= { outlet26PDU8 5 }

energy26PDU8 OBJECT-TYPE
SYNTAX INTEGER (0..65535)
ACCESS read-only
STATUS optional
DESCRIPTION
        " "
::= { outlet26PDU8 6 }

switch27PDU8 OBJECT-TYPE
SYNTAX INTEGER (0..3)
ACCESS read-write
STATUS optional
DESCRIPTION
        " "
::= { outlet27PDU8 1 }

voltage27PDU8 OBJECT-TYPE
SYNTAX INTEGER (0..65535)
ACCESS read-only
STATUS optional
DESCRIPTION
        " "
::= { outlet27PDU8 2 }

current27PDU8 OBJECT-TYPE
SYNTAX INTEGER (0..65535)
ACCESS read-only
STATUS optional
DESCRIPTION
        " "
::= { outlet27PDU8 3 }

power27PDU8 OBJECT-TYPE
SYNTAX INTEGER (0..65535)
ACCESS read-only
STATUS optional
DESCRIPTION
        " "
::= { outlet27PDU8 4 }

pf27PDU8 OBJECT-TYPE
SYNTAX INTEGER (0..65535)
ACCESS read-only
STATUS optional
DESCRIPTION
        " "
::= { outlet27PDU8 5 }

energy27PDU8 OBJECT-TYPE
SYNTAX INTEGER (0..65535)
ACCESS read-only
STATUS optional
DESCRIPTION
        " "
::= { outlet27PDU8 6 }

switch28PDU8 OBJECT-TYPE
SYNTAX INTEGER (0..3)
ACCESS read-write
STATUS optional
DESCRIPTION
        " "
::= { outlet28PDU8 1 }

voltage28PDU8 OBJECT-TYPE
SYNTAX INTEGER (0..65535)
ACCESS read-only
STATUS optional
DESCRIPTION
        " "
::= { outlet28PDU8 2 }

current28PDU8 OBJECT-TYPE
SYNTAX INTEGER (0..65535)
ACCESS read-only
STATUS optional
DESCRIPTION
        " "
::= { outlet28PDU8 3 }

power28PDU8 OBJECT-TYPE
SYNTAX INTEGER (0..65535)
ACCESS read-only
STATUS optional
DESCRIPTION
        " "
::= { outlet28PDU8 4 }

pf28PDU8 OBJECT-TYPE
SYNTAX INTEGER (0..65535)
ACCESS read-only
STATUS optional
DESCRIPTION
        " "
::= { outlet28PDU8 5 }

energy28PDU8 OBJECT-TYPE
SYNTAX INTEGER (0..65535)
ACCESS read-only
STATUS optional
DESCRIPTION
        " "
::= { outlet28PDU8 6 }

switch29PDU8 OBJECT-TYPE
SYNTAX INTEGER (0..3)
ACCESS read-write
STATUS optional
DESCRIPTION
        " "
::= { outlet29PDU8 1 }

voltage29PDU8 OBJECT-TYPE
SYNTAX INTEGER (0..65535)
ACCESS read-only
STATUS optional
DESCRIPTION
        " "
::= { outlet29PDU8 2 }

current29PDU8 OBJECT-TYPE
SYNTAX INTEGER (0..65535)
ACCESS read-only
STATUS optional
DESCRIPTION
        " "
::= { outlet29PDU8 3 }

power29PDU8 OBJECT-TYPE
SYNTAX INTEGER (0..65535)
ACCESS read-only
STATUS optional
DESCRIPTION
        " "
::= { outlet29PDU8 4 }

pf29PDU8 OBJECT-TYPE
SYNTAX INTEGER (0..65535)
ACCESS read-only
STATUS optional
DESCRIPTION
        " "
::= { outlet29PDU8 5 }

energy29PDU8 OBJECT-TYPE
SYNTAX INTEGER (0..65535)
ACCESS read-only
STATUS optional
DESCRIPTION
        " "
::= { outlet29PDU8 6 }

switch30PDU8 OBJECT-TYPE
SYNTAX INTEGER (0..3)
ACCESS read-write
STATUS optional
DESCRIPTION
        " "
::= { outlet30PDU8 1 }

voltage30PDU8 OBJECT-TYPE
SYNTAX INTEGER (0..65535)
ACCESS read-only
STATUS optional
DESCRIPTION
        " "
::= { outlet30PDU8 2 }

current30PDU8 OBJECT-TYPE
SYNTAX INTEGER (0..65535)
ACCESS read-only
STATUS optional
DESCRIPTION
        " "
::= { outlet30PDU8 3 }

power30PDU8 OBJECT-TYPE
SYNTAX INTEGER (0..65535)
ACCESS read-only
STATUS optional
DESCRIPTION
        " "
::= { outlet30PDU8 4 }

pf30PDU8 OBJECT-TYPE
SYNTAX INTEGER (0..65535)
ACCESS read-only
STATUS optional
DESCRIPTION
        " "
::= { outlet30PDU8 5 }

energy30PDU8 OBJECT-TYPE
SYNTAX INTEGER (0..65535)
ACCESS read-only
STATUS optional
DESCRIPTION
        " "
::= { outlet30PDU8 6 }

switch31PDU8 OBJECT-TYPE
SYNTAX INTEGER (0..3)
ACCESS read-write
STATUS optional
DESCRIPTION
        " "
::= { outlet31PDU8 1 }

voltage31PDU8 OBJECT-TYPE
SYNTAX INTEGER (0..65535)
ACCESS read-only
STATUS optional
DESCRIPTION
        " "
::= { outlet31PDU8 2 }

current31PDU8 OBJECT-TYPE
SYNTAX INTEGER (0..65535)
ACCESS read-only
STATUS optional
DESCRIPTION
        " "
::= { outlet31PDU8 3 }

power31PDU8 OBJECT-TYPE
SYNTAX INTEGER (0..65535)
ACCESS read-only
STATUS optional
DESCRIPTION
        " "
::= { outlet31PDU8 4 }

pf31PDU8 OBJECT-TYPE
SYNTAX INTEGER (0..65535)
ACCESS read-only
STATUS optional
DESCRIPTION
        " "
::= { outlet31PDU8 5 }

energy31PDU8 OBJECT-TYPE
SYNTAX INTEGER (0..65535)
ACCESS read-only
STATUS optional
DESCRIPTION
        " "
::= { outlet31PDU8 6 }

switch32PDU8 OBJECT-TYPE
SYNTAX INTEGER (0..3)
ACCESS read-write
STATUS optional
DESCRIPTION
        " "
::= { outlet32PDU8 1 }

voltage32PDU8 OBJECT-TYPE
SYNTAX INTEGER (0..65535)
ACCESS read-only
STATUS optional
DESCRIPTION
        " "
::= { outlet32PDU8 2 }

current32PDU8 OBJECT-TYPE
SYNTAX INTEGER (0..65535)
ACCESS read-only
STATUS optional
DESCRIPTION
        " "
::= { outlet32PDU8 3 }

power32PDU8 OBJECT-TYPE
SYNTAX INTEGER (0..65535)
ACCESS read-only
STATUS optional
DESCRIPTION
        " "
::= { outlet32PDU8 4 }

pf32PDU8 OBJECT-TYPE
SYNTAX INTEGER (0..65535)
ACCESS read-only
STATUS optional
DESCRIPTION
        " "
::= { outlet32PDU8 5 }

energy32PDU8 OBJECT-TYPE
SYNTAX INTEGER (0..65535)
ACCESS read-only
STATUS optional
DESCRIPTION
        " "
::= { outlet32PDU8 6 }

switch33PDU8 OBJECT-TYPE
SYNTAX INTEGER (0..3)
ACCESS read-write
STATUS optional
DESCRIPTION
        " "
::= { outlet33PDU8 1 }

voltage33PDU8 OBJECT-TYPE
SYNTAX INTEGER (0..65535)
ACCESS read-only
STATUS optional
DESCRIPTION
        " "
::= { outlet33PDU8 2 }

current33PDU8 OBJECT-TYPE
SYNTAX INTEGER (0..65535)
ACCESS read-only
STATUS optional
DESCRIPTION
        " "
::= { outlet33PDU8 3 }

power33PDU8 OBJECT-TYPE
SYNTAX INTEGER (0..65535)
ACCESS read-only
STATUS optional
DESCRIPTION
        " "
::= { outlet33PDU8 4 }

pf33PDU8 OBJECT-TYPE
SYNTAX INTEGER (0..65535)
ACCESS read-only
STATUS optional
DESCRIPTION
        " "
::= { outlet33PDU8 5 }

energy33PDU8 OBJECT-TYPE
SYNTAX INTEGER (0..65535)
ACCESS read-only
STATUS optional
DESCRIPTION
        " "
::= { outlet33PDU8 6 }

switch34PDU8 OBJECT-TYPE
SYNTAX INTEGER (0..3)
ACCESS read-write
STATUS optional
DESCRIPTION
        " "
::= { outlet34PDU8 1 }

voltage34PDU8 OBJECT-TYPE
SYNTAX INTEGER (0..65535)
ACCESS read-only
STATUS optional
DESCRIPTION
        " "
::= { outlet34PDU8 2 }

current34PDU8 OBJECT-TYPE
SYNTAX INTEGER (0..65535)
ACCESS read-only
STATUS optional
DESCRIPTION
        " "
::= { outlet34PDU8 3 }

power34PDU8 OBJECT-TYPE
SYNTAX INTEGER (0..65535)
ACCESS read-only
STATUS optional
DESCRIPTION
        " "
::= { outlet34PDU8 4 }

pf34PDU8 OBJECT-TYPE
SYNTAX INTEGER (0..65535)
ACCESS read-only
STATUS optional
DESCRIPTION
        " "
::= { outlet34PDU8 5 }

energy34PDU8 OBJECT-TYPE
SYNTAX INTEGER (0..65535)
ACCESS read-only
STATUS optional
DESCRIPTION
        " "
::= { outlet34PDU8 6 }

switch35PDU8 OBJECT-TYPE
SYNTAX INTEGER (0..3)
ACCESS read-write
STATUS optional
DESCRIPTION
        " "
::= { outlet35PDU8 1 }

voltage35PDU8 OBJECT-TYPE
SYNTAX INTEGER (0..65535)
ACCESS read-only
STATUS optional
DESCRIPTION
        " "
::= { outlet35PDU8 2 }

current35PDU8 OBJECT-TYPE
SYNTAX INTEGER (0..65535)
ACCESS read-only
STATUS optional
DESCRIPTION
        " "
::= { outlet35PDU8 3 }

power35PDU8 OBJECT-TYPE
SYNTAX INTEGER (0..65535)
ACCESS read-only
STATUS optional
DESCRIPTION
        " "
::= { outlet35PDU8 4 }

pf35PDU8 OBJECT-TYPE
SYNTAX INTEGER (0..65535)
ACCESS read-only
STATUS optional
DESCRIPTION
        " "
::= { outlet35PDU8 5 }

energy35PDU8 OBJECT-TYPE
SYNTAX INTEGER (0..65535)
ACCESS read-only
STATUS optional
DESCRIPTION
        " "
::= { outlet35PDU8 6 }

switch36PDU8 OBJECT-TYPE
SYNTAX INTEGER (0..3)
ACCESS read-write
STATUS optional
DESCRIPTION
        " "
::= { outlet36PDU8 1 }

voltage36PDU8 OBJECT-TYPE
SYNTAX INTEGER (0..65535)
ACCESS read-only
STATUS optional
DESCRIPTION
        " "
::= { outlet36PDU8 2 }

current36PDU8 OBJECT-TYPE
SYNTAX INTEGER (0..65535)
ACCESS read-only
STATUS optional
DESCRIPTION
        " "
::= { outlet36PDU8 3 }

power36PDU8 OBJECT-TYPE
SYNTAX INTEGER (0..65535)
ACCESS read-only
STATUS optional
DESCRIPTION
        " "
::= { outlet36PDU8 4 }

pf36PDU8 OBJECT-TYPE
SYNTAX INTEGER (0..65535)
ACCESS read-only
STATUS optional
DESCRIPTION
        " "
::= { outlet36PDU8 5 }

energy36PDU8 OBJECT-TYPE
SYNTAX INTEGER (0..65535)
ACCESS read-only
STATUS optional
DESCRIPTION
        " "
::= { outlet36PDU8 6 }

sensor1 OBJECT IDENTIFIER ::= { pdu8 4 }

temperature1PDU8 OBJECT-TYPE
SYNTAX INTEGER (0..65535)
ACCESS read-only
STATUS optional
DESCRIPTION
        " "
::= { sensor1 1 }

humidity1PDU8 OBJECT-TYPE
SYNTAX INTEGER (0..65535)
ACCESS read-only
STATUS optional
DESCRIPTION
        " "
::= { sensor1 2 }

temperature2PDU8 OBJECT-TYPE
SYNTAX INTEGER (0..65535)
ACCESS read-only
STATUS optional
DESCRIPTION
        " "
::= { sensor1 3 }

humidity2PDU8 OBJECT-TYPE
SYNTAX INTEGER (0..65535)
ACCESS read-only
STATUS optional
DESCRIPTION
        " "
::= { sensor1 4 }

inputStatus1PDU8 OBJECT-TYPE
SYNTAX INTEGER (0..1)
ACCESS read-only
STATUS optional
DESCRIPTION
        " "
::= { sensor1 5 }

inputStatus2PDU8 OBJECT-TYPE
SYNTAX INTEGER (0..1)
ACCESS read-only
STATUS optional
DESCRIPTION
        " "
::= { sensor1 6 }

inputStatus3PDU8 OBJECT-TYPE
SYNTAX INTEGER (0..1)
ACCESS read-only
STATUS optional
DESCRIPTION
        " "
::= { sensor1 7 }

inputStatus4PDU8 OBJECT-TYPE
SYNTAX INTEGER (0..1)
ACCESS read-only
STATUS optional
DESCRIPTION
        " "
::= { sensor1 8 }

doStatus1PDU8 OBJECT-TYPE
SYNTAX INTEGER (0..1)
ACCESS read-only
STATUS optional
DESCRIPTION
        " "
::= { sensor1 9 }

doStatus2PDU8 OBJECT-TYPE
SYNTAX INTEGER (0..1)
ACCESS read-only
STATUS optional
DESCRIPTION
        " "
::= { sensor1 10 }

baseinfo1 OBJECT IDENTIFIER ::= { pdu9 1 }

cascadeAlarmPDU9 OBJECT-TYPE
SYNTAX INTEGER (0..3)
ACCESS read-only
STATUS optional
DESCRIPTION
        " "
::= { baseinfo1 1 }

deviceNamePDU9 OBJECT-TYPE
SYNTAX DisplayString (SIZE (32))
ACCESS read-write
STATUS optional
DESCRIPTION
        " "
::= { baseinfo1 2 }

outletNumberPDU9 OBJECT-TYPE
SYNTAX INTEGER (0..36)
ACCESS read-only
STATUS optional
DESCRIPTION
        " "
::= { baseinfo1 3 }

temphum1WarnStatPDU9 OBJECT-TYPE
SYNTAX INTEGER (0..127)
ACCESS read-only
STATUS optional
DESCRIPTION
        " "
::= { baseinfo1 4 }

temphum2WarnStatPDU9 OBJECT-TYPE
SYNTAX INTEGER (0..127)
ACCESS read-only
STATUS optional
DESCRIPTION
        " "
::= { baseinfo1 5 }

input1WarnStatPDU9 OBJECT-TYPE
SYNTAX INTEGER (0..1)
ACCESS read-only
STATUS optional
DESCRIPTION
        " "
::= { baseinfo1 6 }

input2WarnStatPDU9 OBJECT-TYPE
SYNTAX INTEGER (0..1)
ACCESS read-only
STATUS optional
DESCRIPTION
        " "
::= { baseinfo1 7 }

input3WarnStatPDU9 OBJECT-TYPE
SYNTAX INTEGER (0..1)
ACCESS read-only
STATUS optional
DESCRIPTION
        " "
::= { baseinfo1 8 }

input4WarnStatPDU9 OBJECT-TYPE
SYNTAX INTEGER (0..1)
ACCESS read-only
STATUS optional
DESCRIPTION
        " "
::= { baseinfo1 9 }

currentL1WarnStatPDU9 OBJECT-TYPE
SYNTAX INTEGER (0..127)
ACCESS read-only
STATUS optional
DESCRIPTION
        " "
::= { baseinfo1 10 }

currentL2WarnStatPDU9 OBJECT-TYPE
SYNTAX INTEGER (0..127)
ACCESS read-only
STATUS optional
DESCRIPTION
        " "
::= { baseinfo1 11 }

currentL3WarnStatPDU9 OBJECT-TYPE
SYNTAX INTEGER (0..127)
ACCESS read-only
STATUS optional
DESCRIPTION
        " "
::= { baseinfo1 12 }

voltageL1WarnStatPDU9 OBJECT-TYPE
SYNTAX INTEGER (0..127)
ACCESS read-only
STATUS optional
DESCRIPTION
        " "
::= { baseinfo1 13 }

voltageL2WarnStatPDU9 OBJECT-TYPE
SYNTAX INTEGER (0..127)
ACCESS read-only
STATUS optional
DESCRIPTION
        " "
::= { baseinfo1 14 }

voltageL3WarnStatPDU9 OBJECT-TYPE
SYNTAX INTEGER (0..127)
ACCESS read-only
STATUS optional
DESCRIPTION
        " "
::= { baseinfo1 15 }

outlet1WarnStatPDU9 OBJECT-TYPE
SYNTAX INTEGER (0..127)
ACCESS read-only
STATUS optional
DESCRIPTION
        " "
::= { baseinfo1 16 }

outlet2WarnStatPDU9 OBJECT-TYPE
SYNTAX INTEGER (0..127)
ACCESS read-only
STATUS optional
DESCRIPTION
        " "
::= { baseinfo1 17 }

outlet3WarnStatPDU9 OBJECT-TYPE
SYNTAX INTEGER (0..127)
ACCESS read-only
STATUS optional
DESCRIPTION
        " "
::= { baseinfo1 18 }

outlet4WarnStatPDU9 OBJECT-TYPE
SYNTAX INTEGER (0..127)
ACCESS read-only
STATUS optional
DESCRIPTION
        " "
::= { baseinfo1 19 }

outlet5WarnStatPDU9 OBJECT-TYPE
SYNTAX INTEGER (0..127)
ACCESS read-only
STATUS optional
DESCRIPTION
        " "
::= { baseinfo1 20 }

outlet6WarnStatPDU9 OBJECT-TYPE
SYNTAX INTEGER (0..127)
ACCESS read-only
STATUS optional
DESCRIPTION
        " "
::= { baseinfo1 21 }

outlet7WarnStatPDU9 OBJECT-TYPE
SYNTAX INTEGER (0..127)
ACCESS read-only
STATUS optional
DESCRIPTION
        " "
::= { baseinfo1 22 }

outlet8WarnStatPDU9 OBJECT-TYPE
SYNTAX INTEGER (0..127)
ACCESS read-only
STATUS optional
DESCRIPTION
        " "
::= { baseinfo1 23 }

outlet9WarnStatPDU9 OBJECT-TYPE
SYNTAX INTEGER (0..127)
ACCESS read-only
STATUS optional
DESCRIPTION
        " "
::= { baseinfo1 24 }

outlet10WarnStatPDU9 OBJECT-TYPE
SYNTAX INTEGER (0..127)
ACCESS read-only
STATUS optional
DESCRIPTION
        " "
::= { baseinfo1 25 }

outlet11WarnStatPDU9 OBJECT-TYPE
SYNTAX INTEGER (0..127)
ACCESS read-only
STATUS optional
DESCRIPTION
        " "
::= { baseinfo1 26 }

outlet12WarnStatPDU9 OBJECT-TYPE
SYNTAX INTEGER (0..127)
ACCESS read-only
STATUS optional
DESCRIPTION
        " "
::= { baseinfo1 27 }

outlet13WarnStatPDU9 OBJECT-TYPE
SYNTAX INTEGER (0..127)
ACCESS read-only
STATUS optional
DESCRIPTION
        " "
::= { baseinfo1 28 }

outlet14WarnStatPDU9 OBJECT-TYPE
SYNTAX INTEGER (0..127)
ACCESS read-only
STATUS optional
DESCRIPTION
        " "
::= { baseinfo1 29 }

outlet15WarnStatPDU9 OBJECT-TYPE
SYNTAX INTEGER (0..127)
ACCESS read-only
STATUS optional
DESCRIPTION
        " "
::= { baseinfo1 30 }

outlet16WarnStatPDU9 OBJECT-TYPE
SYNTAX INTEGER (0..127)
ACCESS read-only
STATUS optional
DESCRIPTION
        " "
::= { baseinfo1 31 }

outlet17WarnStatPDU9 OBJECT-TYPE
SYNTAX INTEGER (0..127)
ACCESS read-only
STATUS optional
DESCRIPTION
        " "
::= { baseinfo1 32 }

outlet18WarnStatPDU9 OBJECT-TYPE
SYNTAX INTEGER (0..127)
ACCESS read-only
STATUS optional
DESCRIPTION
        " "
::= { baseinfo1 33 }

outlet19WarnStatPDU9 OBJECT-TYPE
SYNTAX INTEGER (0..127)
ACCESS read-only
STATUS optional
DESCRIPTION
        " "
::= { baseinfo1 34 }

outlet20WarnStatPDU9 OBJECT-TYPE
SYNTAX INTEGER (0..127)
ACCESS read-only
STATUS optional
DESCRIPTION
        " "
::= { baseinfo1 35 }

outlet21WarnStatPDU9 OBJECT-TYPE
SYNTAX INTEGER (0..127)
ACCESS read-only
STATUS optional
DESCRIPTION
        " "
::= { baseinfo1 36 }

outlet22WarnStatPDU9 OBJECT-TYPE
SYNTAX INTEGER (0..127)
ACCESS read-only
STATUS optional
DESCRIPTION
        " "
::= { baseinfo1 37 }

outlet23WarnStatPDU9 OBJECT-TYPE
SYNTAX INTEGER (0..127)
ACCESS read-only
STATUS optional
DESCRIPTION
        " "
::= { baseinfo1 38 }

outlet24WarnStatPDU9 OBJECT-TYPE
SYNTAX INTEGER (0..127)
ACCESS read-only
STATUS optional
DESCRIPTION
        " "
::= { baseinfo1 39 }

outlet25WarnStatPDU9 OBJECT-TYPE
SYNTAX INTEGER (0..127)
ACCESS read-only
STATUS optional
DESCRIPTION
        " "
::= { baseinfo1 40 }

outlet26WarnStatPDU9 OBJECT-TYPE
SYNTAX INTEGER (0..127)
ACCESS read-only
STATUS optional
DESCRIPTION
        " "
::= { baseinfo1 41 }

outlet27WarnStatPDU9 OBJECT-TYPE
SYNTAX INTEGER (0..127)
ACCESS read-only
STATUS optional
DESCRIPTION
        " "
::= { baseinfo1 42 }

outlet28WarnStatPDU9 OBJECT-TYPE
SYNTAX INTEGER (0..127)
ACCESS read-only
STATUS optional
DESCRIPTION
        " "
::= { baseinfo1 43 }

outlet29WarnStatPDU9 OBJECT-TYPE
SYNTAX INTEGER (0..127)
ACCESS read-only
STATUS optional
DESCRIPTION
        " "
::= { baseinfo1 44 }

outlet30WarnStatPDU9 OBJECT-TYPE
SYNTAX INTEGER (0..127)
ACCESS read-only
STATUS optional
DESCRIPTION
        " "
::= { baseinfo1 45 }

outlet31WarnStatPDU9 OBJECT-TYPE
SYNTAX INTEGER (0..127)
ACCESS read-only
STATUS optional
DESCRIPTION
        " "
::= { baseinfo1 46 }

outlet32WarnStatPDU9 OBJECT-TYPE
SYNTAX INTEGER (0..127)
ACCESS read-only
STATUS optional
DESCRIPTION
        " "
::= { baseinfo1 47 }

outlet33WarnStatPDU9 OBJECT-TYPE
SYNTAX INTEGER (0..127)
ACCESS read-only
STATUS optional
DESCRIPTION
        " "
::= { baseinfo1 48 }

outlet34WarnStatPDU9 OBJECT-TYPE
SYNTAX INTEGER (0..127)
ACCESS read-only
STATUS optional
DESCRIPTION
        " "
::= { baseinfo1 49 }

outlet35WarnStatPDU9 OBJECT-TYPE
SYNTAX INTEGER (0..127)
ACCESS read-only
STATUS optional
DESCRIPTION
        " "
::= { baseinfo1 50 }

outlet36WarnStatPDU9 OBJECT-TYPE
SYNTAX INTEGER (0..127)
ACCESS read-only
STATUS optional
DESCRIPTION
        " "
::= { baseinfo1 51 }

input1 OBJECT IDENTIFIER ::= { pdu9 2 }

currentL1PDU9 OBJECT-TYPE
SYNTAX INTEGER (0..65535)
ACCESS read-only
STATUS optional
DESCRIPTION
        " "
::= { input1 1 }

voltageL1PDU9 OBJECT-TYPE
SYNTAX INTEGER (0..65535)
ACCESS read-only
STATUS optional
DESCRIPTION
        " "
::= { input1 2 }

powerL1PDU9 OBJECT-TYPE
SYNTAX INTEGER (0..65535)
ACCESS read-only
STATUS optional
DESCRIPTION
        " "
::= { input1 3 }

pfL1PDU9 OBJECT-TYPE
SYNTAX INTEGER (0..65535)
ACCESS read-only
STATUS optional
DESCRIPTION
        " "
::= { input1 4 }

energyL1PDU9 OBJECT-TYPE
SYNTAX INTEGER (0..65535)
ACCESS read-only
STATUS optional
DESCRIPTION
        " "
::= { input1 5 }

currentL2PDU9 OBJECT-TYPE
SYNTAX INTEGER (0..65535)
ACCESS read-only
STATUS optional
DESCRIPTION
        " "
::= { input1 6 }

voltageL2PDU9 OBJECT-TYPE
SYNTAX INTEGER (0..65535)
ACCESS read-only
STATUS optional
DESCRIPTION
        " "
::= { input1 7 }

powerL2PDU9 OBJECT-TYPE
SYNTAX INTEGER (0..65535)
ACCESS read-only
STATUS optional
DESCRIPTION
        " "
::= { input1 8 }

pfL2PDU9 OBJECT-TYPE
SYNTAX INTEGER (0..65535)
ACCESS read-only
STATUS optional
DESCRIPTION
        " "
::= { input1 9 }

energyL2PDU9 OBJECT-TYPE
SYNTAX INTEGER (0..65535)
ACCESS read-only
STATUS optional
DESCRIPTION
        " "
::= { input1 10 }

currentL3PDU9 OBJECT-TYPE
SYNTAX INTEGER (0..65535)
ACCESS read-only
STATUS optional
DESCRIPTION
        " "
::= { input1 11 }

voltageL3PDU9 OBJECT-TYPE
SYNTAX INTEGER (0..65535)
ACCESS read-only
STATUS optional
DESCRIPTION
        " "
::= { input1 12 }

powerL3PDU9 OBJECT-TYPE
SYNTAX INTEGER (0..65535)
ACCESS read-only
STATUS optional
DESCRIPTION
        " "
::= { input1 13 }

pfL3PDU9 OBJECT-TYPE
SYNTAX INTEGER (0..65535)
ACCESS read-only
STATUS optional
DESCRIPTION
        " "
::= { input1 14 }

energyL3PDU9 OBJECT-TYPE
SYNTAX INTEGER (0..65535)
ACCESS read-only
STATUS optional
DESCRIPTION
        " "
::= { input1 15 }

outletinfo1 OBJECT IDENTIFIER ::= { pdu9 3 }

outlet1PDU9 OBJECT IDENTIFIER ::= { outletinfo1 1 }

outlet2PDU9 OBJECT IDENTIFIER ::= { outletinfo1 2 }

outlet3PDU9 OBJECT IDENTIFIER ::= { outletinfo1 3 }

outlet4PDU9 OBJECT IDENTIFIER ::= { outletinfo1 4 }

outlet5PDU9 OBJECT IDENTIFIER ::= { outletinfo1 5 }

outlet6PDU9 OBJECT IDENTIFIER ::= { outletinfo1 6 }

outlet7PDU9 OBJECT IDENTIFIER ::= { outletinfo1 7 }

outlet8PDU9 OBJECT IDENTIFIER ::= { outletinfo1 8 }

outlet9PDU9 OBJECT IDENTIFIER ::= { outletinfo1 9 }

outlet10PDU9 OBJECT IDENTIFIER ::= { outletinfo1 10 }

outlet11PDU9 OBJECT IDENTIFIER ::= { outletinfo1 11 }

outlet12PDU9 OBJECT IDENTIFIER ::= { outletinfo1 12 }

outlet13PDU9 OBJECT IDENTIFIER ::= { outletinfo1 13 }

outlet14PDU9 OBJECT IDENTIFIER ::= { outletinfo1 14 }

outlet15PDU9 OBJECT IDENTIFIER ::= { outletinfo1 15 }

outlet16PDU9 OBJECT IDENTIFIER ::= { outletinfo1 16 }

outlet17PDU9 OBJECT IDENTIFIER ::= { outletinfo1 17 }

outlet18PDU9 OBJECT IDENTIFIER ::= { outletinfo1 18 }

outlet19PDU9 OBJECT IDENTIFIER ::= { outletinfo1 19 }

outlet20PDU9 OBJECT IDENTIFIER ::= { outletinfo1 20 }

outlet21PDU9 OBJECT IDENTIFIER ::= { outletinfo1 21 }

outlet22PDU9 OBJECT IDENTIFIER ::= { outletinfo1 22 }

outlet23PDU9 OBJECT IDENTIFIER ::= { outletinfo1 23 }

outlet24PDU9 OBJECT IDENTIFIER ::= { outletinfo1 24 }

outlet25PDU9 OBJECT IDENTIFIER ::= { outletinfo1 25 }

outlet26PDU9 OBJECT IDENTIFIER ::= { outletinfo1 26 }

outlet27PDU9 OBJECT IDENTIFIER ::= { outletinfo1 27 }

outlet28PDU9 OBJECT IDENTIFIER ::= { outletinfo1 28 }

outlet29PDU9 OBJECT IDENTIFIER ::= { outletinfo1 29 }

outlet30PDU9 OBJECT IDENTIFIER ::= { outletinfo1 30 }

outlet31PDU9 OBJECT IDENTIFIER ::= { outletinfo1 31 }

outlet32PDU9 OBJECT IDENTIFIER ::= { outletinfo1 32 }

outlet33PDU9 OBJECT IDENTIFIER ::= { outletinfo1 33 }

outlet34PDU9 OBJECT IDENTIFIER ::= { outletinfo1 34 }

outlet35PDU9 OBJECT IDENTIFIER ::= { outletinfo1 35 }

outlet36PDU9 OBJECT IDENTIFIER ::= { outletinfo1 36 }

switch1PDU9 OBJECT-TYPE
SYNTAX INTEGER (0..3)
ACCESS read-write
STATUS optional
DESCRIPTION
        " "
::= { outlet1PDU9 1 }

voltage1PDU9 OBJECT-TYPE
SYNTAX INTEGER (0..65535)
ACCESS read-only
STATUS optional
DESCRIPTION
        " "
::= { outlet1PDU9 2 }

current1PDU9 OBJECT-TYPE
SYNTAX INTEGER (0..65535)
ACCESS read-only
STATUS optional
DESCRIPTION
        " "
::= { outlet1PDU9 3 }

power1PDU9 OBJECT-TYPE
SYNTAX INTEGER (0..65535)
ACCESS read-only
STATUS optional
DESCRIPTION
        " "
::= { outlet1PDU9 4 }

pf1PDU9 OBJECT-TYPE
SYNTAX INTEGER (0..65535)
ACCESS read-only
STATUS optional
DESCRIPTION
        " "
::= { outlet1PDU9 5 }

energy1PDU9 OBJECT-TYPE
SYNTAX INTEGER (0..65535)
ACCESS read-only
STATUS optional
DESCRIPTION
        " "
::= { outlet1PDU9 6 }

switch2PDU9 OBJECT-TYPE
SYNTAX INTEGER (0..3)
ACCESS read-write
STATUS optional
DESCRIPTION
        " "
::= { outlet2PDU9 1 }

voltage2PDU9 OBJECT-TYPE
SYNTAX INTEGER (0..65535)
ACCESS read-only
STATUS optional
DESCRIPTION
        " "
::= { outlet2PDU9 2 }

current2PDU9 OBJECT-TYPE
SYNTAX INTEGER (0..65535)
ACCESS read-only
STATUS optional
DESCRIPTION
        " "
::= { outlet2PDU9 3 }

power2PDU9 OBJECT-TYPE
SYNTAX INTEGER (0..65535)
ACCESS read-only
STATUS optional
DESCRIPTION
        " "
::= { outlet2PDU9 4 }

pf2PDU9 OBJECT-TYPE
SYNTAX INTEGER (0..65535)
ACCESS read-only
STATUS optional
DESCRIPTION
        " "
::= { outlet2PDU9 5 }

energy2PDU9 OBJECT-TYPE
SYNTAX INTEGER (0..65535)
ACCESS read-only
STATUS optional
DESCRIPTION
        " "
::= { outlet2PDU9 6 }

switch3PDU9 OBJECT-TYPE
SYNTAX INTEGER (0..3)
ACCESS read-write
STATUS optional
DESCRIPTION
        " "
::= { outlet3PDU9 1 }

voltage3PDU9 OBJECT-TYPE
SYNTAX INTEGER (0..65535)
ACCESS read-only
STATUS optional
DESCRIPTION
        " "
::= { outlet3PDU9 2 }

current3PDU9 OBJECT-TYPE
SYNTAX INTEGER (0..65535)
ACCESS read-only
STATUS optional
DESCRIPTION
        " "
::= { outlet3PDU9 3 }

power3PDU9 OBJECT-TYPE
SYNTAX INTEGER (0..65535)
ACCESS read-only
STATUS optional
DESCRIPTION
        " "
::= { outlet3PDU9 4 }

pf3PDU9 OBJECT-TYPE
SYNTAX INTEGER (0..65535)
ACCESS read-only
STATUS optional
DESCRIPTION
        " "
::= { outlet3PDU9 5 }

energy3PDU9 OBJECT-TYPE
SYNTAX INTEGER (0..65535)
ACCESS read-only
STATUS optional
DESCRIPTION
        " "
::= { outlet3PDU9 6 }

switch4PDU9 OBJECT-TYPE
SYNTAX INTEGER (0..3)
ACCESS read-write
STATUS optional
DESCRIPTION
        " "
::= { outlet4PDU9 1 }

voltage4PDU9 OBJECT-TYPE
SYNTAX INTEGER (0..65535)
ACCESS read-only
STATUS optional
DESCRIPTION
        " "
::= { outlet4PDU9 2 }

current4PDU9 OBJECT-TYPE
SYNTAX INTEGER (0..65535)
ACCESS read-only
STATUS optional
DESCRIPTION
        " "
::= { outlet4PDU9 3 }

power4PDU9 OBJECT-TYPE
SYNTAX INTEGER (0..65535)
ACCESS read-only
STATUS optional
DESCRIPTION
        " "
::= { outlet4PDU9 4 }

pf4PDU9 OBJECT-TYPE
SYNTAX INTEGER (0..65535)
ACCESS read-only
STATUS optional
DESCRIPTION
        " "
::= { outlet4PDU9 5 }

energy4PDU9 OBJECT-TYPE
SYNTAX INTEGER (0..65535)
ACCESS read-only
STATUS optional
DESCRIPTION
        " "
::= { outlet4PDU9 6 }

switch5PDU9 OBJECT-TYPE
SYNTAX INTEGER (0..3)
ACCESS read-write
STATUS optional
DESCRIPTION
        " "
::= { outlet5PDU9 1 }

voltage5PDU9 OBJECT-TYPE
SYNTAX INTEGER (0..65535)
ACCESS read-only
STATUS optional
DESCRIPTION
        " "
::= { outlet5PDU9 2 }

current5PDU9 OBJECT-TYPE
SYNTAX INTEGER (0..65535)
ACCESS read-only
STATUS optional
DESCRIPTION
        " "
::= { outlet5PDU9 3 }

power5PDU9 OBJECT-TYPE
SYNTAX INTEGER (0..65535)
ACCESS read-only
STATUS optional
DESCRIPTION
        " "
::= { outlet5PDU9 4 }

pf5PDU9 OBJECT-TYPE
SYNTAX INTEGER (0..65535)
ACCESS read-only
STATUS optional
DESCRIPTION
        " "
::= { outlet5PDU9 5 }

energy5PDU9 OBJECT-TYPE
SYNTAX INTEGER (0..65535)
ACCESS read-only
STATUS optional
DESCRIPTION
        " "
::= { outlet5PDU9 6 }

switch6PDU9 OBJECT-TYPE
SYNTAX INTEGER (0..3)
ACCESS read-write
STATUS optional
DESCRIPTION
        " "
::= { outlet6PDU9 1 }

voltage6PDU9 OBJECT-TYPE
SYNTAX INTEGER (0..65535)
ACCESS read-only
STATUS optional
DESCRIPTION
        " "
::= { outlet6PDU9 2 }

current6PDU9 OBJECT-TYPE
SYNTAX INTEGER (0..65535)
ACCESS read-only
STATUS optional
DESCRIPTION
        " "
::= { outlet6PDU9 3 }

power6PDU9 OBJECT-TYPE
SYNTAX INTEGER (0..65535)
ACCESS read-only
STATUS optional
DESCRIPTION
        " "
::= { outlet6PDU9 4 }

pf6PDU9 OBJECT-TYPE
SYNTAX INTEGER (0..65535)
ACCESS read-only
STATUS optional
DESCRIPTION
        " "
::= { outlet6PDU9 5 }

energy6PDU9 OBJECT-TYPE
SYNTAX INTEGER (0..65535)
ACCESS read-only
STATUS optional
DESCRIPTION
        " "
::= { outlet6PDU9 6 }

switch7PDU9 OBJECT-TYPE
SYNTAX INTEGER (0..3)
ACCESS read-write
STATUS optional
DESCRIPTION
        " "
::= { outlet7PDU9 1 }

voltage7PDU9 OBJECT-TYPE
SYNTAX INTEGER (0..65535)
ACCESS read-only
STATUS optional
DESCRIPTION
        " "
::= { outlet7PDU9 2 }

current7PDU9 OBJECT-TYPE
SYNTAX INTEGER (0..65535)
ACCESS read-only
STATUS optional
DESCRIPTION
        " "
::= { outlet7PDU9 3 }

power7PDU9 OBJECT-TYPE
SYNTAX INTEGER (0..65535)
ACCESS read-only
STATUS optional
DESCRIPTION
        " "
::= { outlet7PDU9 4 }

pf7PDU9 OBJECT-TYPE
SYNTAX INTEGER (0..65535)
ACCESS read-only
STATUS optional
DESCRIPTION
        " "
::= { outlet7PDU9 5 }

energy7PDU9 OBJECT-TYPE
SYNTAX INTEGER (0..65535)
ACCESS read-only
STATUS optional
DESCRIPTION
        " "
::= { outlet7PDU9 6 }

switch8PDU9 OBJECT-TYPE
SYNTAX INTEGER (0..3)
ACCESS read-write
STATUS optional
DESCRIPTION
        " "
::= { outlet8PDU9 1 }

voltage8PDU9 OBJECT-TYPE
SYNTAX INTEGER (0..65535)
ACCESS read-only
STATUS optional
DESCRIPTION
        " "
::= { outlet8PDU9 2 }

current8PDU9 OBJECT-TYPE
SYNTAX INTEGER (0..65535)
ACCESS read-only
STATUS optional
DESCRIPTION
        " "
::= { outlet8PDU9 3 }

power8PDU9 OBJECT-TYPE
SYNTAX INTEGER (0..65535)
ACCESS read-only
STATUS optional
DESCRIPTION
        " "
::= { outlet8PDU9 4 }

pf8PDU9 OBJECT-TYPE
SYNTAX INTEGER (0..65535)
ACCESS read-only
STATUS optional
DESCRIPTION
        " "
::= { outlet8PDU9 5 }

energy8PDU9 OBJECT-TYPE
SYNTAX INTEGER (0..65535)
ACCESS read-only
STATUS optional
DESCRIPTION
        " "
::= { outlet8PDU9 6 }

switch9PDU9 OBJECT-TYPE
SYNTAX INTEGER (0..3)
ACCESS read-write
STATUS optional
DESCRIPTION
        " "
::= { outlet9PDU9 1 }

voltage9PDU9 OBJECT-TYPE
SYNTAX INTEGER (0..65535)
ACCESS read-only
STATUS optional
DESCRIPTION
        " "
::= { outlet9PDU9 2 }

current9PDU9 OBJECT-TYPE
SYNTAX INTEGER (0..65535)
ACCESS read-only
STATUS optional
DESCRIPTION
        " "
::= { outlet9PDU9 3 }

power9PDU9 OBJECT-TYPE
SYNTAX INTEGER (0..65535)
ACCESS read-only
STATUS optional
DESCRIPTION
        " "
::= { outlet9PDU9 4 }

pf9PDU9 OBJECT-TYPE
SYNTAX INTEGER (0..65535)
ACCESS read-only
STATUS optional
DESCRIPTION
        " "
::= { outlet9PDU9 5 }

energy9PDU9 OBJECT-TYPE
SYNTAX INTEGER (0..65535)
ACCESS read-only
STATUS optional
DESCRIPTION
        " "
::= { outlet9PDU9 6 }

switch10PDU9 OBJECT-TYPE
SYNTAX INTEGER (0..3)
ACCESS read-write
STATUS optional
DESCRIPTION
        " "
::= { outlet10PDU9 1 }

voltage10PDU9 OBJECT-TYPE
SYNTAX INTEGER (0..65535)
ACCESS read-only
STATUS optional
DESCRIPTION
        " "
::= { outlet10PDU9 2 }

current10PDU9 OBJECT-TYPE
SYNTAX INTEGER (0..65535)
ACCESS read-only
STATUS optional
DESCRIPTION
        " "
::= { outlet10PDU9 3 }

power10PDU9 OBJECT-TYPE
SYNTAX INTEGER (0..65535)
ACCESS read-only
STATUS optional
DESCRIPTION
        " "
::= { outlet10PDU9 4 }

pf10PDU9 OBJECT-TYPE
SYNTAX INTEGER (0..65535)
ACCESS read-only
STATUS optional
DESCRIPTION
        " "
::= { outlet10PDU9 5 }

energy10PDU9 OBJECT-TYPE
SYNTAX INTEGER (0..65535)
ACCESS read-only
STATUS optional
DESCRIPTION
        " "
::= { outlet10PDU9 6 }

switch11PDU9 OBJECT-TYPE
SYNTAX INTEGER (0..3)
ACCESS read-write
STATUS optional
DESCRIPTION
        " "
::= { outlet11PDU9 1 }

voltage11PDU9 OBJECT-TYPE
SYNTAX INTEGER (0..65535)
ACCESS read-only
STATUS optional
DESCRIPTION
        " "
::= { outlet11PDU9 2 }

current11PDU9 OBJECT-TYPE
SYNTAX INTEGER (0..65535)
ACCESS read-only
STATUS optional
DESCRIPTION
        " "
::= { outlet11PDU9 3 }

power11PDU9 OBJECT-TYPE
SYNTAX INTEGER (0..65535)
ACCESS read-only
STATUS optional
DESCRIPTION
        " "
::= { outlet11PDU9 4 }

pf11PDU9 OBJECT-TYPE
SYNTAX INTEGER (0..65535)
ACCESS read-only
STATUS optional
DESCRIPTION
        " "
::= { outlet11PDU9 5 }

energy11PDU9 OBJECT-TYPE
SYNTAX INTEGER (0..65535)
ACCESS read-only
STATUS optional
DESCRIPTION
        " "
::= { outlet11PDU9 6 }

switch12PDU9 OBJECT-TYPE
SYNTAX INTEGER (0..3)
ACCESS read-write
STATUS optional
DESCRIPTION
        " "
::= { outlet12PDU9 1 }

voltage12PDU9 OBJECT-TYPE
SYNTAX INTEGER (0..65535)
ACCESS read-only
STATUS optional
DESCRIPTION
        " "
::= { outlet12PDU9 2 }

current12PDU9 OBJECT-TYPE
SYNTAX INTEGER (0..65535)
ACCESS read-only
STATUS optional
DESCRIPTION
        " "
::= { outlet12PDU9 3 }

power12PDU9 OBJECT-TYPE
SYNTAX INTEGER (0..65535)
ACCESS read-only
STATUS optional
DESCRIPTION
        " "
::= { outlet12PDU9 4 }

pf12PDU9 OBJECT-TYPE
SYNTAX INTEGER (0..65535)
ACCESS read-only
STATUS optional
DESCRIPTION
        " "
::= { outlet12PDU9 5 }

energy12PDU9 OBJECT-TYPE
SYNTAX INTEGER (0..65535)
ACCESS read-only
STATUS optional
DESCRIPTION
        " "
::= { outlet12PDU9 6 }

switch13PDU9 OBJECT-TYPE
SYNTAX INTEGER (0..3)
ACCESS read-write
STATUS optional
DESCRIPTION
        " "
::= { outlet13PDU9 1 }

voltage13PDU9 OBJECT-TYPE
SYNTAX INTEGER (0..65535)
ACCESS read-only
STATUS optional
DESCRIPTION
        " "
::= { outlet13PDU9 2 }

current13PDU9 OBJECT-TYPE
SYNTAX INTEGER (0..65535)
ACCESS read-only
STATUS optional
DESCRIPTION
        " "
::= { outlet13PDU9 3 }

power13PDU9 OBJECT-TYPE
SYNTAX INTEGER (0..65535)
ACCESS read-only
STATUS optional
DESCRIPTION
        " "
::= { outlet13PDU9 4 }

pf13PDU9 OBJECT-TYPE
SYNTAX INTEGER (0..65535)
ACCESS read-only
STATUS optional
DESCRIPTION
        " "
::= { outlet13PDU9 5 }

energy13PDU9 OBJECT-TYPE
SYNTAX INTEGER (0..65535)
ACCESS read-only
STATUS optional
DESCRIPTION
        " "
::= { outlet13PDU9 6 }

switch14PDU9 OBJECT-TYPE
SYNTAX INTEGER (0..3)
ACCESS read-write
STATUS optional
DESCRIPTION
        " "
::= { outlet14PDU9 1 }

voltage14PDU9 OBJECT-TYPE
SYNTAX INTEGER (0..65535)
ACCESS read-only
STATUS optional
DESCRIPTION
        " "
::= { outlet14PDU9 2 }

current14PDU9 OBJECT-TYPE
SYNTAX INTEGER (0..65535)
ACCESS read-only
STATUS optional
DESCRIPTION
        " "
::= { outlet14PDU9 3 }

power14PDU9 OBJECT-TYPE
SYNTAX INTEGER (0..65535)
ACCESS read-only
STATUS optional
DESCRIPTION
        " "
::= { outlet14PDU9 4 }

pf14PDU9 OBJECT-TYPE
SYNTAX INTEGER (0..65535)
ACCESS read-only
STATUS optional
DESCRIPTION
        " "
::= { outlet14PDU9 5 }

energy14PDU9 OBJECT-TYPE
SYNTAX INTEGER (0..65535)
ACCESS read-only
STATUS optional
DESCRIPTION
        " "
::= { outlet14PDU9 6 }

switch15PDU9 OBJECT-TYPE
SYNTAX INTEGER (0..3)
ACCESS read-write
STATUS optional
DESCRIPTION
        " "
::= { outlet15PDU9 1 }

voltage15PDU9 OBJECT-TYPE
SYNTAX INTEGER (0..65535)
ACCESS read-only
STATUS optional
DESCRIPTION
        " "
::= { outlet15PDU9 2 }

current15PDU9 OBJECT-TYPE
SYNTAX INTEGER (0..65535)
ACCESS read-only
STATUS optional
DESCRIPTION
        " "
::= { outlet15PDU9 3 }

power15PDU9 OBJECT-TYPE
SYNTAX INTEGER (0..65535)
ACCESS read-only
STATUS optional
DESCRIPTION
        " "
::= { outlet15PDU9 4 }

pf15PDU9 OBJECT-TYPE
SYNTAX INTEGER (0..65535)
ACCESS read-only
STATUS optional
DESCRIPTION
        " "
::= { outlet15PDU9 5 }

energy15PDU9 OBJECT-TYPE
SYNTAX INTEGER (0..65535)
ACCESS read-only
STATUS optional
DESCRIPTION
        " "
::= { outlet15PDU9 6 }

switch16PDU9 OBJECT-TYPE
SYNTAX INTEGER (0..3)
ACCESS read-write
STATUS optional
DESCRIPTION
        " "
::= { outlet16PDU9 1 }

voltage16PDU9 OBJECT-TYPE
SYNTAX INTEGER (0..65535)
ACCESS read-only
STATUS optional
DESCRIPTION
        " "
::= { outlet16PDU9 2 }

current16PDU9 OBJECT-TYPE
SYNTAX INTEGER (0..65535)
ACCESS read-only
STATUS optional
DESCRIPTION
        " "
::= { outlet16PDU9 3 }

power16PDU9 OBJECT-TYPE
SYNTAX INTEGER (0..65535)
ACCESS read-only
STATUS optional
DESCRIPTION
        " "
::= { outlet16PDU9 4 }

pf16PDU9 OBJECT-TYPE
SYNTAX INTEGER (0..65535)
ACCESS read-only
STATUS optional
DESCRIPTION
        " "
::= { outlet16PDU9 5 }

energy16PDU9 OBJECT-TYPE
SYNTAX INTEGER (0..65535)
ACCESS read-only
STATUS optional
DESCRIPTION
        " "
::= { outlet16PDU9 6 }

switch17PDU9 OBJECT-TYPE
SYNTAX INTEGER (0..3)
ACCESS read-write
STATUS optional
DESCRIPTION
        " "
::= { outlet17PDU9 1 }

voltage17PDU9 OBJECT-TYPE
SYNTAX INTEGER (0..65535)
ACCESS read-only
STATUS optional
DESCRIPTION
        " "
::= { outlet17PDU9 2 }

current17PDU9 OBJECT-TYPE
SYNTAX INTEGER (0..65535)
ACCESS read-only
STATUS optional
DESCRIPTION
        " "
::= { outlet17PDU9 3 }

power17PDU9 OBJECT-TYPE
SYNTAX INTEGER (0..65535)
ACCESS read-only
STATUS optional
DESCRIPTION
        " "
::= { outlet17PDU9 4 }

pf17PDU9 OBJECT-TYPE
SYNTAX INTEGER (0..65535)
ACCESS read-only
STATUS optional
DESCRIPTION
        " "
::= { outlet17PDU9 5 }

energy17PDU9 OBJECT-TYPE
SYNTAX INTEGER (0..65535)
ACCESS read-only
STATUS optional
DESCRIPTION
        " "
::= { outlet17PDU9 6 }

switch18PDU9 OBJECT-TYPE
SYNTAX INTEGER (0..3)
ACCESS read-write
STATUS optional
DESCRIPTION
        " "
::= { outlet18PDU9 1 }

voltage18PDU9 OBJECT-TYPE
SYNTAX INTEGER (0..65535)
ACCESS read-only
STATUS optional
DESCRIPTION
        " "
::= { outlet18PDU9 2 }

current18PDU9 OBJECT-TYPE
SYNTAX INTEGER (0..65535)
ACCESS read-only
STATUS optional
DESCRIPTION
        " "
::= { outlet18PDU9 3 }

power18PDU9 OBJECT-TYPE
SYNTAX INTEGER (0..65535)
ACCESS read-only
STATUS optional
DESCRIPTION
        " "
::= { outlet18PDU9 4 }

pf18PDU9 OBJECT-TYPE
SYNTAX INTEGER (0..65535)
ACCESS read-only
STATUS optional
DESCRIPTION
        " "
::= { outlet18PDU9 5 }

energy18PDU9 OBJECT-TYPE
SYNTAX INTEGER (0..65535)
ACCESS read-only
STATUS optional
DESCRIPTION
        " "
::= { outlet18PDU9 6 }

switch19PDU9 OBJECT-TYPE
SYNTAX INTEGER (0..3)
ACCESS read-write
STATUS optional
DESCRIPTION
        " "
::= { outlet19PDU9 1 }

voltage19PDU9 OBJECT-TYPE
SYNTAX INTEGER (0..65535)
ACCESS read-only
STATUS optional
DESCRIPTION
        " "
::= { outlet19PDU9 2 }

current19PDU9 OBJECT-TYPE
SYNTAX INTEGER (0..65535)
ACCESS read-only
STATUS optional
DESCRIPTION
        " "
::= { outlet19PDU9 3 }

power19PDU9 OBJECT-TYPE
SYNTAX INTEGER (0..65535)
ACCESS read-only
STATUS optional
DESCRIPTION
        " "
::= { outlet19PDU9 4 }

pf19PDU9 OBJECT-TYPE
SYNTAX INTEGER (0..65535)
ACCESS read-only
STATUS optional
DESCRIPTION
        " "
::= { outlet19PDU9 5 }

energy19PDU9 OBJECT-TYPE
SYNTAX INTEGER (0..65535)
ACCESS read-only
STATUS optional
DESCRIPTION
        " "
::= { outlet19PDU9 6 }

switch20PDU9 OBJECT-TYPE
SYNTAX INTEGER (0..3)
ACCESS read-write
STATUS optional
DESCRIPTION
        " "
::= { outlet20PDU9 1 }

voltage20PDU9 OBJECT-TYPE
SYNTAX INTEGER (0..65535)
ACCESS read-only
STATUS optional
DESCRIPTION
        " "
::= { outlet20PDU9 2 }

current20PDU9 OBJECT-TYPE
SYNTAX INTEGER (0..65535)
ACCESS read-only
STATUS optional
DESCRIPTION
        " "
::= { outlet20PDU9 3 }

power20PDU9 OBJECT-TYPE
SYNTAX INTEGER (0..65535)
ACCESS read-only
STATUS optional
DESCRIPTION
        " "
::= { outlet20PDU9 4 }

pf20PDU9 OBJECT-TYPE
SYNTAX INTEGER (0..65535)
ACCESS read-only
STATUS optional
DESCRIPTION
        " "
::= { outlet20PDU9 5 }

energy20PDU9 OBJECT-TYPE
SYNTAX INTEGER (0..65535)
ACCESS read-only
STATUS optional
DESCRIPTION
        " "
::= { outlet20PDU9 6 }

switch21PDU9 OBJECT-TYPE
SYNTAX INTEGER (0..3)
ACCESS read-write
STATUS optional
DESCRIPTION
        " "
::= { outlet21PDU9 1 }

voltage21PDU9 OBJECT-TYPE
SYNTAX INTEGER (0..65535)
ACCESS read-only
STATUS optional
DESCRIPTION
        " "
::= { outlet21PDU9 2 }

current21PDU9 OBJECT-TYPE
SYNTAX INTEGER (0..65535)
ACCESS read-only
STATUS optional
DESCRIPTION
        " "
::= { outlet21PDU9 3 }

power21PDU9 OBJECT-TYPE
SYNTAX INTEGER (0..65535)
ACCESS read-only
STATUS optional
DESCRIPTION
        " "
::= { outlet21PDU9 4 }

pf21PDU9 OBJECT-TYPE
SYNTAX INTEGER (0..65535)
ACCESS read-only
STATUS optional
DESCRIPTION
        " "
::= { outlet21PDU9 5 }

energy21PDU9 OBJECT-TYPE
SYNTAX INTEGER (0..65535)
ACCESS read-only
STATUS optional
DESCRIPTION
        " "
::= { outlet21PDU9 6 }

switch22PDU9 OBJECT-TYPE
SYNTAX INTEGER (0..3)
ACCESS read-write
STATUS optional
DESCRIPTION
        " "
::= { outlet22PDU9 1 }

voltage22PDU9 OBJECT-TYPE
SYNTAX INTEGER (0..65535)
ACCESS read-only
STATUS optional
DESCRIPTION
        " "
::= { outlet22PDU9 2 }

current22PDU9 OBJECT-TYPE
SYNTAX INTEGER (0..65535)
ACCESS read-only
STATUS optional
DESCRIPTION
        " "
::= { outlet22PDU9 3 }

power22PDU9 OBJECT-TYPE
SYNTAX INTEGER (0..65535)
ACCESS read-only
STATUS optional
DESCRIPTION
        " "
::= { outlet22PDU9 4 }

pf22PDU9 OBJECT-TYPE
SYNTAX INTEGER (0..65535)
ACCESS read-only
STATUS optional
DESCRIPTION
        " "
::= { outlet22PDU9 5 }

energy22PDU9 OBJECT-TYPE
SYNTAX INTEGER (0..65535)
ACCESS read-only
STATUS optional
DESCRIPTION
        " "
::= { outlet22PDU9 6 }

switch23PDU9 OBJECT-TYPE
SYNTAX INTEGER (0..3)
ACCESS read-write
STATUS optional
DESCRIPTION
        " "
::= { outlet23PDU9 1 }

voltage23PDU9 OBJECT-TYPE
SYNTAX INTEGER (0..65535)
ACCESS read-only
STATUS optional
DESCRIPTION
        " "
::= { outlet23PDU9 2 }

current23PDU9 OBJECT-TYPE
SYNTAX INTEGER (0..65535)
ACCESS read-only
STATUS optional
DESCRIPTION
        " "
::= { outlet23PDU9 3 }

power23PDU9 OBJECT-TYPE
SYNTAX INTEGER (0..65535)
ACCESS read-only
STATUS optional
DESCRIPTION
        " "
::= { outlet23PDU9 4 }

pf23PDU9 OBJECT-TYPE
SYNTAX INTEGER (0..65535)
ACCESS read-only
STATUS optional
DESCRIPTION
        " "
::= { outlet23PDU9 5 }

energy23PDU9 OBJECT-TYPE
SYNTAX INTEGER (0..65535)
ACCESS read-only
STATUS optional
DESCRIPTION
        " "
::= { outlet23PDU9 6 }

switch24PDU9 OBJECT-TYPE
SYNTAX INTEGER (0..3)
ACCESS read-write
STATUS optional
DESCRIPTION
        " "
::= { outlet24PDU9 1 }

voltage24PDU9 OBJECT-TYPE
SYNTAX INTEGER (0..65535)
ACCESS read-only
STATUS optional
DESCRIPTION
        " "
::= { outlet24PDU9 2 }

current24PDU9 OBJECT-TYPE
SYNTAX INTEGER (0..65535)
ACCESS read-only
STATUS optional
DESCRIPTION
        " "
::= { outlet24PDU9 3 }

power24PDU9 OBJECT-TYPE
SYNTAX INTEGER (0..65535)
ACCESS read-only
STATUS optional
DESCRIPTION
        " "
::= { outlet24PDU9 4 }

pf24PDU9 OBJECT-TYPE
SYNTAX INTEGER (0..65535)
ACCESS read-only
STATUS optional
DESCRIPTION
        " "
::= { outlet24PDU9 5 }

energy24PDU9 OBJECT-TYPE
SYNTAX INTEGER (0..65535)
ACCESS read-only
STATUS optional
DESCRIPTION
        " "
::= { outlet24PDU9 6 }

switch25PDU9 OBJECT-TYPE
SYNTAX INTEGER (0..3)
ACCESS read-write
STATUS optional
DESCRIPTION
        " "
::= { outlet25PDU9 1 }

voltage25PDU9 OBJECT-TYPE
SYNTAX INTEGER (0..65535)
ACCESS read-only
STATUS optional
DESCRIPTION
        " "
::= { outlet25PDU9 2 }

current25PDU9 OBJECT-TYPE
SYNTAX INTEGER (0..65535)
ACCESS read-only
STATUS optional
DESCRIPTION
        " "
::= { outlet25PDU9 3 }

power25PDU9 OBJECT-TYPE
SYNTAX INTEGER (0..65535)
ACCESS read-only
STATUS optional
DESCRIPTION
        " "
::= { outlet25PDU9 4 }

pf25PDU9 OBJECT-TYPE
SYNTAX INTEGER (0..65535)
ACCESS read-only
STATUS optional
DESCRIPTION
        " "
::= { outlet25PDU9 5 }

energy25PDU9 OBJECT-TYPE
SYNTAX INTEGER (0..65535)
ACCESS read-only
STATUS optional
DESCRIPTION
        " "
::= { outlet25PDU9 6 }

switch26PDU9 OBJECT-TYPE
SYNTAX INTEGER (0..3)
ACCESS read-write
STATUS optional
DESCRIPTION
        " "
::= { outlet26PDU9 1 }

voltage26PDU9 OBJECT-TYPE
SYNTAX INTEGER (0..65535)
ACCESS read-only
STATUS optional
DESCRIPTION
        " "
::= { outlet26PDU9 2 }

current26PDU9 OBJECT-TYPE
SYNTAX INTEGER (0..65535)
ACCESS read-only
STATUS optional
DESCRIPTION
        " "
::= { outlet26PDU9 3 }

power26PDU9 OBJECT-TYPE
SYNTAX INTEGER (0..65535)
ACCESS read-only
STATUS optional
DESCRIPTION
        " "
::= { outlet26PDU9 4 }

pf26PDU9 OBJECT-TYPE
SYNTAX INTEGER (0..65535)
ACCESS read-only
STATUS optional
DESCRIPTION
        " "
::= { outlet26PDU9 5 }

energy26PDU9 OBJECT-TYPE
SYNTAX INTEGER (0..65535)
ACCESS read-only
STATUS optional
DESCRIPTION
        " "
::= { outlet26PDU9 6 }

switch27PDU9 OBJECT-TYPE
SYNTAX INTEGER (0..3)
ACCESS read-write
STATUS optional
DESCRIPTION
        " "
::= { outlet27PDU9 1 }

voltage27PDU9 OBJECT-TYPE
SYNTAX INTEGER (0..65535)
ACCESS read-only
STATUS optional
DESCRIPTION
        " "
::= { outlet27PDU9 2 }

current27PDU9 OBJECT-TYPE
SYNTAX INTEGER (0..65535)
ACCESS read-only
STATUS optional
DESCRIPTION
        " "
::= { outlet27PDU9 3 }

power27PDU9 OBJECT-TYPE
SYNTAX INTEGER (0..65535)
ACCESS read-only
STATUS optional
DESCRIPTION
        " "
::= { outlet27PDU9 4 }

pf27PDU9 OBJECT-TYPE
SYNTAX INTEGER (0..65535)
ACCESS read-only
STATUS optional
DESCRIPTION
        " "
::= { outlet27PDU9 5 }

energy27PDU9 OBJECT-TYPE
SYNTAX INTEGER (0..65535)
ACCESS read-only
STATUS optional
DESCRIPTION
        " "
::= { outlet27PDU9 6 }

switch28PDU9 OBJECT-TYPE
SYNTAX INTEGER (0..3)
ACCESS read-write
STATUS optional
DESCRIPTION
        " "
::= { outlet28PDU9 1 }

voltage28PDU9 OBJECT-TYPE
SYNTAX INTEGER (0..65535)
ACCESS read-only
STATUS optional
DESCRIPTION
        " "
::= { outlet28PDU9 2 }

current28PDU9 OBJECT-TYPE
SYNTAX INTEGER (0..65535)
ACCESS read-only
STATUS optional
DESCRIPTION
        " "
::= { outlet28PDU9 3 }

power28PDU9 OBJECT-TYPE
SYNTAX INTEGER (0..65535)
ACCESS read-only
STATUS optional
DESCRIPTION
        " "
::= { outlet28PDU9 4 }

pf28PDU9 OBJECT-TYPE
SYNTAX INTEGER (0..65535)
ACCESS read-only
STATUS optional
DESCRIPTION
        " "
::= { outlet28PDU9 5 }

energy28PDU9 OBJECT-TYPE
SYNTAX INTEGER (0..65535)
ACCESS read-only
STATUS optional
DESCRIPTION
        " "
::= { outlet28PDU9 6 }

switch29PDU9 OBJECT-TYPE
SYNTAX INTEGER (0..3)
ACCESS read-write
STATUS optional
DESCRIPTION
        " "
::= { outlet29PDU9 1 }

voltage29PDU9 OBJECT-TYPE
SYNTAX INTEGER (0..65535)
ACCESS read-only
STATUS optional
DESCRIPTION
        " "
::= { outlet29PDU9 2 }

current29PDU9 OBJECT-TYPE
SYNTAX INTEGER (0..65535)
ACCESS read-only
STATUS optional
DESCRIPTION
        " "
::= { outlet29PDU9 3 }

power29PDU9 OBJECT-TYPE
SYNTAX INTEGER (0..65535)
ACCESS read-only
STATUS optional
DESCRIPTION
        " "
::= { outlet29PDU9 4 }

pf29PDU9 OBJECT-TYPE
SYNTAX INTEGER (0..65535)
ACCESS read-only
STATUS optional
DESCRIPTION
        " "
::= { outlet29PDU9 5 }

energy29PDU9 OBJECT-TYPE
SYNTAX INTEGER (0..65535)
ACCESS read-only
STATUS optional
DESCRIPTION
        " "
::= { outlet29PDU9 6 }

switch30PDU9 OBJECT-TYPE
SYNTAX INTEGER (0..3)
ACCESS read-write
STATUS optional
DESCRIPTION
        " "
::= { outlet30PDU9 1 }

voltage30PDU9 OBJECT-TYPE
SYNTAX INTEGER (0..65535)
ACCESS read-only
STATUS optional
DESCRIPTION
        " "
::= { outlet30PDU9 2 }

current30PDU9 OBJECT-TYPE
SYNTAX INTEGER (0..65535)
ACCESS read-only
STATUS optional
DESCRIPTION
        " "
::= { outlet30PDU9 3 }

power30PDU9 OBJECT-TYPE
SYNTAX INTEGER (0..65535)
ACCESS read-only
STATUS optional
DESCRIPTION
        " "
::= { outlet30PDU9 4 }

pf30PDU9 OBJECT-TYPE
SYNTAX INTEGER (0..65535)
ACCESS read-only
STATUS optional
DESCRIPTION
        " "
::= { outlet30PDU9 5 }

energy30PDU9 OBJECT-TYPE
SYNTAX INTEGER (0..65535)
ACCESS read-only
STATUS optional
DESCRIPTION
        " "
::= { outlet30PDU9 6 }

switch31PDU9 OBJECT-TYPE
SYNTAX INTEGER (0..3)
ACCESS read-write
STATUS optional
DESCRIPTION
        " "
::= { outlet31PDU9 1 }

voltage31PDU9 OBJECT-TYPE
SYNTAX INTEGER (0..65535)
ACCESS read-only
STATUS optional
DESCRIPTION
        " "
::= { outlet31PDU9 2 }

current31PDU9 OBJECT-TYPE
SYNTAX INTEGER (0..65535)
ACCESS read-only
STATUS optional
DESCRIPTION
        " "
::= { outlet31PDU9 3 }

power31PDU9 OBJECT-TYPE
SYNTAX INTEGER (0..65535)
ACCESS read-only
STATUS optional
DESCRIPTION
        " "
::= { outlet31PDU9 4 }

pf31PDU9 OBJECT-TYPE
SYNTAX INTEGER (0..65535)
ACCESS read-only
STATUS optional
DESCRIPTION
        " "
::= { outlet31PDU9 5 }

energy31PDU9 OBJECT-TYPE
SYNTAX INTEGER (0..65535)
ACCESS read-only
STATUS optional
DESCRIPTION
        " "
::= { outlet31PDU9 6 }

switch32PDU9 OBJECT-TYPE
SYNTAX INTEGER (0..3)
ACCESS read-write
STATUS optional
DESCRIPTION
        " "
::= { outlet32PDU9 1 }

voltage32PDU9 OBJECT-TYPE
SYNTAX INTEGER (0..65535)
ACCESS read-only
STATUS optional
DESCRIPTION
        " "
::= { outlet32PDU9 2 }

current32PDU9 OBJECT-TYPE
SYNTAX INTEGER (0..65535)
ACCESS read-only
STATUS optional
DESCRIPTION
        " "
::= { outlet32PDU9 3 }

power32PDU9 OBJECT-TYPE
SYNTAX INTEGER (0..65535)
ACCESS read-only
STATUS optional
DESCRIPTION
        " "
::= { outlet32PDU9 4 }

pf32PDU9 OBJECT-TYPE
SYNTAX INTEGER (0..65535)
ACCESS read-only
STATUS optional
DESCRIPTION
        " "
::= { outlet32PDU9 5 }

energy32PDU9 OBJECT-TYPE
SYNTAX INTEGER (0..65535)
ACCESS read-only
STATUS optional
DESCRIPTION
        " "
::= { outlet32PDU9 6 }

switch33PDU9 OBJECT-TYPE
SYNTAX INTEGER (0..3)
ACCESS read-write
STATUS optional
DESCRIPTION
        " "
::= { outlet33PDU9 1 }

voltage33PDU9 OBJECT-TYPE
SYNTAX INTEGER (0..65535)
ACCESS read-only
STATUS optional
DESCRIPTION
        " "
::= { outlet33PDU9 2 }

current33PDU9 OBJECT-TYPE
SYNTAX INTEGER (0..65535)
ACCESS read-only
STATUS optional
DESCRIPTION
        " "
::= { outlet33PDU9 3 }

power33PDU9 OBJECT-TYPE
SYNTAX INTEGER (0..65535)
ACCESS read-only
STATUS optional
DESCRIPTION
        " "
::= { outlet33PDU9 4 }

pf33PDU9 OBJECT-TYPE
SYNTAX INTEGER (0..65535)
ACCESS read-only
STATUS optional
DESCRIPTION
        " "
::= { outlet33PDU9 5 }

energy33PDU9 OBJECT-TYPE
SYNTAX INTEGER (0..65535)
ACCESS read-only
STATUS optional
DESCRIPTION
        " "
::= { outlet33PDU9 6 }

switch34PDU9 OBJECT-TYPE
SYNTAX INTEGER (0..3)
ACCESS read-write
STATUS optional
DESCRIPTION
        " "
::= { outlet34PDU9 1 }

voltage34PDU9 OBJECT-TYPE
SYNTAX INTEGER (0..65535)
ACCESS read-only
STATUS optional
DESCRIPTION
        " "
::= { outlet34PDU9 2 }

current34PDU9 OBJECT-TYPE
SYNTAX INTEGER (0..65535)
ACCESS read-only
STATUS optional
DESCRIPTION
        " "
::= { outlet34PDU9 3 }

power34PDU9 OBJECT-TYPE
SYNTAX INTEGER (0..65535)
ACCESS read-only
STATUS optional
DESCRIPTION
        " "
::= { outlet34PDU9 4 }

pf34PDU9 OBJECT-TYPE
SYNTAX INTEGER (0..65535)
ACCESS read-only
STATUS optional
DESCRIPTION
        " "
::= { outlet34PDU9 5 }

energy34PDU9 OBJECT-TYPE
SYNTAX INTEGER (0..65535)
ACCESS read-only
STATUS optional
DESCRIPTION
        " "
::= { outlet34PDU9 6 }

switch35PDU9 OBJECT-TYPE
SYNTAX INTEGER (0..3)
ACCESS read-write
STATUS optional
DESCRIPTION
        " "
::= { outlet35PDU9 1 }

voltage35PDU9 OBJECT-TYPE
SYNTAX INTEGER (0..65535)
ACCESS read-only
STATUS optional
DESCRIPTION
        " "
::= { outlet35PDU9 2 }

current35PDU9 OBJECT-TYPE
SYNTAX INTEGER (0..65535)
ACCESS read-only
STATUS optional
DESCRIPTION
        " "
::= { outlet35PDU9 3 }

power35PDU9 OBJECT-TYPE
SYNTAX INTEGER (0..65535)
ACCESS read-only
STATUS optional
DESCRIPTION
        " "
::= { outlet35PDU9 4 }

pf35PDU9 OBJECT-TYPE
SYNTAX INTEGER (0..65535)
ACCESS read-only
STATUS optional
DESCRIPTION
        " "
::= { outlet35PDU9 5 }

energy35PDU9 OBJECT-TYPE
SYNTAX INTEGER (0..65535)
ACCESS read-only
STATUS optional
DESCRIPTION
        " "
::= { outlet35PDU9 6 }

switch36PDU9 OBJECT-TYPE
SYNTAX INTEGER (0..3)
ACCESS read-write
STATUS optional
DESCRIPTION
        " "
::= { outlet36PDU9 1 }

voltage36PDU9 OBJECT-TYPE
SYNTAX INTEGER (0..65535)
ACCESS read-only
STATUS optional
DESCRIPTION
        " "
::= { outlet36PDU9 2 }

current36PDU9 OBJECT-TYPE
SYNTAX INTEGER (0..65535)
ACCESS read-only
STATUS optional
DESCRIPTION
        " "
::= { outlet36PDU9 3 }

power36PDU9 OBJECT-TYPE
SYNTAX INTEGER (0..65535)
ACCESS read-only
STATUS optional
DESCRIPTION
        " "
::= { outlet36PDU9 4 }

pf36PDU9 OBJECT-TYPE
SYNTAX INTEGER (0..65535)
ACCESS read-only
STATUS optional
DESCRIPTION
        " "
::= { outlet36PDU9 5 }

energy36PDU9 OBJECT-TYPE
SYNTAX INTEGER (0..65535)
ACCESS read-only
STATUS optional
DESCRIPTION
        " "
::= { outlet36PDU9 6 }

sensor1 OBJECT IDENTIFIER ::= { pdu9 4 }

temperature1PDU9 OBJECT-TYPE
SYNTAX INTEGER (0..65535)
ACCESS read-only
STATUS optional
DESCRIPTION
        " "
::= { sensor1 1 }

humidity1PDU9 OBJECT-TYPE
SYNTAX INTEGER (0..65535)
ACCESS read-only
STATUS optional
DESCRIPTION
        " "
::= { sensor1 2 }

temperature2PDU9 OBJECT-TYPE
SYNTAX INTEGER (0..65535)
ACCESS read-only
STATUS optional
DESCRIPTION
        " "
::= { sensor1 3 }

humidity2PDU9 OBJECT-TYPE
SYNTAX INTEGER (0..65535)
ACCESS read-only
STATUS optional
DESCRIPTION
        " "
::= { sensor1 4 }

inputStatus1PDU9 OBJECT-TYPE
SYNTAX INTEGER (0..1)
ACCESS read-only
STATUS optional
DESCRIPTION
        " "
::= { sensor1 5 }

inputStatus2PDU9 OBJECT-TYPE
SYNTAX INTEGER (0..1)
ACCESS read-only
STATUS optional
DESCRIPTION
        " "
::= { sensor1 6 }

inputStatus3PDU9 OBJECT-TYPE
SYNTAX INTEGER (0..1)
ACCESS read-only
STATUS optional
DESCRIPTION
        " "
::= { sensor1 7 }

inputStatus4PDU9 OBJECT-TYPE
SYNTAX INTEGER (0..1)
ACCESS read-only
STATUS optional
DESCRIPTION
        " "
::= { sensor1 8 }

doStatus1PDU9 OBJECT-TYPE
SYNTAX INTEGER (0..1)
ACCESS read-only
STATUS optional
DESCRIPTION
        " "
::= { sensor1 9 }

doStatus2PDU9 OBJECT-TYPE
SYNTAX INTEGER (0..1)
ACCESS read-only
STATUS optional
DESCRIPTION
        " "
::= { sensor1 10 }

baseinfo1 OBJECT IDENTIFIER ::= { pdu10 1 }

cascadeAlarmPDU10 OBJECT-TYPE
SYNTAX INTEGER (0..3)
ACCESS read-only
STATUS optional
DESCRIPTION
        " "
::= { baseinfo1 1 }

deviceNamePDU10 OBJECT-TYPE
SYNTAX DisplayString (SIZE (32))
ACCESS read-write
STATUS optional
DESCRIPTION
        " "
::= { baseinfo1 2 }

outletNumberPDU10 OBJECT-TYPE
SYNTAX INTEGER (0..36)
ACCESS read-only
STATUS optional
DESCRIPTION
        " "
::= { baseinfo1 3 }

temphum1WarnStatPDU10 OBJECT-TYPE
SYNTAX INTEGER (0..127)
ACCESS read-only
STATUS optional
DESCRIPTION
        " "
::= { baseinfo1 4 }

temphum2WarnStatPDU10 OBJECT-TYPE
SYNTAX INTEGER (0..127)
ACCESS read-only
STATUS optional
DESCRIPTION
        " "
::= { baseinfo1 5 }

input1WarnStatPDU10 OBJECT-TYPE
SYNTAX INTEGER (0..1)
ACCESS read-only
STATUS optional
DESCRIPTION
        " "
::= { baseinfo1 6 }

input2WarnStatPDU10 OBJECT-TYPE
SYNTAX INTEGER (0..1)
ACCESS read-only
STATUS optional
DESCRIPTION
        " "
::= { baseinfo1 7 }

input3WarnStatPDU10 OBJECT-TYPE
SYNTAX INTEGER (0..1)
ACCESS read-only
STATUS optional
DESCRIPTION
        " "
::= { baseinfo1 8 }

input4WarnStatPDU10 OBJECT-TYPE
SYNTAX INTEGER (0..1)
ACCESS read-only
STATUS optional
DESCRIPTION
        " "
::= { baseinfo1 9 }

currentL1WarnStatPDU10 OBJECT-TYPE
SYNTAX INTEGER (0..127)
ACCESS read-only
STATUS optional
DESCRIPTION
        " "
::= { baseinfo1 10 }

currentL2WarnStatPDU10 OBJECT-TYPE
SYNTAX INTEGER (0..127)
ACCESS read-only
STATUS optional
DESCRIPTION
        " "
::= { baseinfo1 11 }

currentL3WarnStatPDU10 OBJECT-TYPE
SYNTAX INTEGER (0..127)
ACCESS read-only
STATUS optional
DESCRIPTION
        " "
::= { baseinfo1 12 }

voltageL1WarnStatPDU10 OBJECT-TYPE
SYNTAX INTEGER (0..127)
ACCESS read-only
STATUS optional
DESCRIPTION
        " "
::= { baseinfo1 13 }

voltageL2WarnStatPDU10 OBJECT-TYPE
SYNTAX INTEGER (0..127)
ACCESS read-only
STATUS optional
DESCRIPTION
        " "
::= { baseinfo1 14 }

voltageL3WarnStatPDU10 OBJECT-TYPE
SYNTAX INTEGER (0..127)
ACCESS read-only
STATUS optional
DESCRIPTION
        " "
::= { baseinfo1 15 }

outlet1WarnStatPDU10 OBJECT-TYPE
SYNTAX INTEGER (0..127)
ACCESS read-only
STATUS optional
DESCRIPTION
        " "
::= { baseinfo1 16 }

outlet2WarnStatPDU10 OBJECT-TYPE
SYNTAX INTEGER (0..127)
ACCESS read-only
STATUS optional
DESCRIPTION
        " "
::= { baseinfo1 17 }

outlet3WarnStatPDU10 OBJECT-TYPE
SYNTAX INTEGER (0..127)
ACCESS read-only
STATUS optional
DESCRIPTION
        " "
::= { baseinfo1 18 }

outlet4WarnStatPDU10 OBJECT-TYPE
SYNTAX INTEGER (0..127)
ACCESS read-only
STATUS optional
DESCRIPTION
        " "
::= { baseinfo1 19 }

outlet5WarnStatPDU10 OBJECT-TYPE
SYNTAX INTEGER (0..127)
ACCESS read-only
STATUS optional
DESCRIPTION
        " "
::= { baseinfo1 20 }

outlet6WarnStatPDU10 OBJECT-TYPE
SYNTAX INTEGER (0..127)
ACCESS read-only
STATUS optional
DESCRIPTION
        " "
::= { baseinfo1 21 }

outlet7WarnStatPDU10 OBJECT-TYPE
SYNTAX INTEGER (0..127)
ACCESS read-only
STATUS optional
DESCRIPTION
        " "
::= { baseinfo1 22 }

outlet8WarnStatPDU10 OBJECT-TYPE
SYNTAX INTEGER (0..127)
ACCESS read-only
STATUS optional
DESCRIPTION
        " "
::= { baseinfo1 23 }

outlet9WarnStatPDU10 OBJECT-TYPE
SYNTAX INTEGER (0..127)
ACCESS read-only
STATUS optional
DESCRIPTION
        " "
::= { baseinfo1 24 }

outlet10WarnStatPDU10 OBJECT-TYPE
SYNTAX INTEGER (0..127)
ACCESS read-only
STATUS optional
DESCRIPTION
        " "
::= { baseinfo1 25 }

outlet11WarnStatPDU10 OBJECT-TYPE
SYNTAX INTEGER (0..127)
ACCESS read-only
STATUS optional
DESCRIPTION
        " "
::= { baseinfo1 26 }

outlet12WarnStatPDU10 OBJECT-TYPE
SYNTAX INTEGER (0..127)
ACCESS read-only
STATUS optional
DESCRIPTION
        " "
::= { baseinfo1 27 }

outlet13WarnStatPDU10 OBJECT-TYPE
SYNTAX INTEGER (0..127)
ACCESS read-only
STATUS optional
DESCRIPTION
        " "
::= { baseinfo1 28 }

outlet14WarnStatPDU10 OBJECT-TYPE
SYNTAX INTEGER (0..127)
ACCESS read-only
STATUS optional
DESCRIPTION
        " "
::= { baseinfo1 29 }

outlet15WarnStatPDU10 OBJECT-TYPE
SYNTAX INTEGER (0..127)
ACCESS read-only
STATUS optional
DESCRIPTION
        " "
::= { baseinfo1 30 }

outlet16WarnStatPDU10 OBJECT-TYPE
SYNTAX INTEGER (0..127)
ACCESS read-only
STATUS optional
DESCRIPTION
        " "
::= { baseinfo1 31 }

outlet17WarnStatPDU10 OBJECT-TYPE
SYNTAX INTEGER (0..127)
ACCESS read-only
STATUS optional
DESCRIPTION
        " "
::= { baseinfo1 32 }

outlet18WarnStatPDU10 OBJECT-TYPE
SYNTAX INTEGER (0..127)
ACCESS read-only
STATUS optional
DESCRIPTION
        " "
::= { baseinfo1 33 }

outlet19WarnStatPDU10 OBJECT-TYPE
SYNTAX INTEGER (0..127)
ACCESS read-only
STATUS optional
DESCRIPTION
        " "
::= { baseinfo1 34 }

outlet20WarnStatPDU10 OBJECT-TYPE
SYNTAX INTEGER (0..127)
ACCESS read-only
STATUS optional
DESCRIPTION
        " "
::= { baseinfo1 35 }

outlet21WarnStatPDU10 OBJECT-TYPE
SYNTAX INTEGER (0..127)
ACCESS read-only
STATUS optional
DESCRIPTION
        " "
::= { baseinfo1 36 }

outlet22WarnStatPDU10 OBJECT-TYPE
SYNTAX INTEGER (0..127)
ACCESS read-only
STATUS optional
DESCRIPTION
        " "
::= { baseinfo1 37 }

outlet23WarnStatPDU10 OBJECT-TYPE
SYNTAX INTEGER (0..127)
ACCESS read-only
STATUS optional
DESCRIPTION
        " "
::= { baseinfo1 38 }

outlet24WarnStatPDU10 OBJECT-TYPE
SYNTAX INTEGER (0..127)
ACCESS read-only
STATUS optional
DESCRIPTION
        " "
::= { baseinfo1 39 }

outlet25WarnStatPDU10 OBJECT-TYPE
SYNTAX INTEGER (0..127)
ACCESS read-only
STATUS optional
DESCRIPTION
        " "
::= { baseinfo1 40 }

outlet26WarnStatPDU10 OBJECT-TYPE
SYNTAX INTEGER (0..127)
ACCESS read-only
STATUS optional
DESCRIPTION
        " "
::= { baseinfo1 41 }

outlet27WarnStatPDU10 OBJECT-TYPE
SYNTAX INTEGER (0..127)
ACCESS read-only
STATUS optional
DESCRIPTION
        " "
::= { baseinfo1 42 }

outlet28WarnStatPDU10 OBJECT-TYPE
SYNTAX INTEGER (0..127)
ACCESS read-only
STATUS optional
DESCRIPTION
        " "
::= { baseinfo1 43 }

outlet29WarnStatPDU10 OBJECT-TYPE
SYNTAX INTEGER (0..127)
ACCESS read-only
STATUS optional
DESCRIPTION
        " "
::= { baseinfo1 44 }

outlet30WarnStatPDU10 OBJECT-TYPE
SYNTAX INTEGER (0..127)
ACCESS read-only
STATUS optional
DESCRIPTION
        " "
::= { baseinfo1 45 }

outlet31WarnStatPDU10 OBJECT-TYPE
SYNTAX INTEGER (0..127)
ACCESS read-only
STATUS optional
DESCRIPTION
        " "
::= { baseinfo1 46 }

outlet32WarnStatPDU10 OBJECT-TYPE
SYNTAX INTEGER (0..127)
ACCESS read-only
STATUS optional
DESCRIPTION
        " "
::= { baseinfo1 47 }

outlet33WarnStatPDU10 OBJECT-TYPE
SYNTAX INTEGER (0..127)
ACCESS read-only
STATUS optional
DESCRIPTION
        " "
::= { baseinfo1 48 }

outlet34WarnStatPDU10 OBJECT-TYPE
SYNTAX INTEGER (0..127)
ACCESS read-only
STATUS optional
DESCRIPTION
        " "
::= { baseinfo1 49 }

outlet35WarnStatPDU10 OBJECT-TYPE
SYNTAX INTEGER (0..127)
ACCESS read-only
STATUS optional
DESCRIPTION
        " "
::= { baseinfo1 50 }

outlet36WarnStatPDU10 OBJECT-TYPE
SYNTAX INTEGER (0..127)
ACCESS read-only
STATUS optional
DESCRIPTION
        " "
::= { baseinfo1 51 }

input1 OBJECT IDENTIFIER ::= { pdu10 2 }

currentL1PDU10 OBJECT-TYPE
SYNTAX INTEGER (0..65535)
ACCESS read-only
STATUS optional
DESCRIPTION
        " "
::= { input1 1 }

voltageL1PDU10 OBJECT-TYPE
SYNTAX INTEGER (0..65535)
ACCESS read-only
STATUS optional
DESCRIPTION
        " "
::= { input1 2 }

powerL1PDU10 OBJECT-TYPE
SYNTAX INTEGER (0..65535)
ACCESS read-only
STATUS optional
DESCRIPTION
        " "
::= { input1 3 }

pfL1PDU10 OBJECT-TYPE
SYNTAX INTEGER (0..65535)
ACCESS read-only
STATUS optional
DESCRIPTION
        " "
::= { input1 4 }

energyL1PDU10 OBJECT-TYPE
SYNTAX INTEGER (0..65535)
ACCESS read-only
STATUS optional
DESCRIPTION
        " "
::= { input1 5 }

currentL2PDU10 OBJECT-TYPE
SYNTAX INTEGER (0..65535)
ACCESS read-only
STATUS optional
DESCRIPTION
        " "
::= { input1 6 }

voltageL2PDU10 OBJECT-TYPE
SYNTAX INTEGER (0..65535)
ACCESS read-only
STATUS optional
DESCRIPTION
        " "
::= { input1 7 }

powerL2PDU10 OBJECT-TYPE
SYNTAX INTEGER (0..65535)
ACCESS read-only
STATUS optional
DESCRIPTION
        " "
::= { input1 8 }

pfL2PDU10 OBJECT-TYPE
SYNTAX INTEGER (0..65535)
ACCESS read-only
STATUS optional
DESCRIPTION
        " "
::= { input1 9 }

energyL2PDU10 OBJECT-TYPE
SYNTAX INTEGER (0..65535)
ACCESS read-only
STATUS optional
DESCRIPTION
        " "
::= { input1 10 }

currentL3PDU10 OBJECT-TYPE
SYNTAX INTEGER (0..65535)
ACCESS read-only
STATUS optional
DESCRIPTION
        " "
::= { input1 11 }

voltageL3PDU10 OBJECT-TYPE
SYNTAX INTEGER (0..65535)
ACCESS read-only
STATUS optional
DESCRIPTION
        " "
::= { input1 12 }

powerL3PDU10 OBJECT-TYPE
SYNTAX INTEGER (0..65535)
ACCESS read-only
STATUS optional
DESCRIPTION
        " "
::= { input1 13 }

pfL3PDU10 OBJECT-TYPE
SYNTAX INTEGER (0..65535)
ACCESS read-only
STATUS optional
DESCRIPTION
        " "
::= { input1 14 }

energyL3PDU10 OBJECT-TYPE
SYNTAX INTEGER (0..65535)
ACCESS read-only
STATUS optional
DESCRIPTION
        " "
::= { input1 15 }

outletinfo1 OBJECT IDENTIFIER ::= { pdu10 3 }

outlet1PDU10 OBJECT IDENTIFIER ::= { outletinfo1 1 }

outlet2PDU10 OBJECT IDENTIFIER ::= { outletinfo1 2 }

outlet3PDU10 OBJECT IDENTIFIER ::= { outletinfo1 3 }

outlet4PDU10 OBJECT IDENTIFIER ::= { outletinfo1 4 }

outlet5PDU10 OBJECT IDENTIFIER ::= { outletinfo1 5 }

outlet6PDU10 OBJECT IDENTIFIER ::= { outletinfo1 6 }

outlet7PDU10 OBJECT IDENTIFIER ::= { outletinfo1 7 }

outlet8PDU10 OBJECT IDENTIFIER ::= { outletinfo1 8 }

outlet9PDU10 OBJECT IDENTIFIER ::= { outletinfo1 9 }

outlet10PDU10 OBJECT IDENTIFIER ::= { outletinfo1 10 }

outlet11PDU10 OBJECT IDENTIFIER ::= { outletinfo1 11 }

outlet12PDU10 OBJECT IDENTIFIER ::= { outletinfo1 12 }

outlet13PDU10 OBJECT IDENTIFIER ::= { outletinfo1 13 }

outlet14PDU10 OBJECT IDENTIFIER ::= { outletinfo1 14 }

outlet15PDU10 OBJECT IDENTIFIER ::= { outletinfo1 15 }

outlet16PDU10 OBJECT IDENTIFIER ::= { outletinfo1 16 }

outlet17PDU10 OBJECT IDENTIFIER ::= { outletinfo1 17 }

outlet18PDU10 OBJECT IDENTIFIER ::= { outletinfo1 18 }

outlet19PDU10 OBJECT IDENTIFIER ::= { outletinfo1 19 }

outlet20PDU10 OBJECT IDENTIFIER ::= { outletinfo1 20 }

outlet21PDU10 OBJECT IDENTIFIER ::= { outletinfo1 21 }

outlet22PDU10 OBJECT IDENTIFIER ::= { outletinfo1 22 }

outlet23PDU10 OBJECT IDENTIFIER ::= { outletinfo1 23 }

outlet24PDU10 OBJECT IDENTIFIER ::= { outletinfo1 24 }

outlet25PDU10 OBJECT IDENTIFIER ::= { outletinfo1 25 }

outlet26PDU10 OBJECT IDENTIFIER ::= { outletinfo1 26 }

outlet27PDU10 OBJECT IDENTIFIER ::= { outletinfo1 27 }

outlet28PDU10 OBJECT IDENTIFIER ::= { outletinfo1 28 }

outlet29PDU10 OBJECT IDENTIFIER ::= { outletinfo1 29 }

outlet30PDU10 OBJECT IDENTIFIER ::= { outletinfo1 30 }

outlet31PDU10 OBJECT IDENTIFIER ::= { outletinfo1 31 }

outlet32PDU10 OBJECT IDENTIFIER ::= { outletinfo1 32 }

outlet33PDU10 OBJECT IDENTIFIER ::= { outletinfo1 33 }

outlet34PDU10 OBJECT IDENTIFIER ::= { outletinfo1 34 }

outlet35PDU10 OBJECT IDENTIFIER ::= { outletinfo1 35 }

outlet36PDU10 OBJECT IDENTIFIER ::= { outletinfo1 36 }

switch1PDU10 OBJECT-TYPE
SYNTAX INTEGER (0..3)
ACCESS read-write
STATUS optional
DESCRIPTION
        " "
::= { outlet1PDU10 1 }

voltage1PDU10 OBJECT-TYPE
SYNTAX INTEGER (0..65535)
ACCESS read-only
STATUS optional
DESCRIPTION
        " "
::= { outlet1PDU10 2 }

current1PDU10 OBJECT-TYPE
SYNTAX INTEGER (0..65535)
ACCESS read-only
STATUS optional
DESCRIPTION
        " "
::= { outlet1PDU10 3 }

power1PDU10 OBJECT-TYPE
SYNTAX INTEGER (0..65535)
ACCESS read-only
STATUS optional
DESCRIPTION
        " "
::= { outlet1PDU10 4 }

pf1PDU10 OBJECT-TYPE
SYNTAX INTEGER (0..65535)
ACCESS read-only
STATUS optional
DESCRIPTION
        " "
::= { outlet1PDU10 5 }

energy1PDU10 OBJECT-TYPE
SYNTAX INTEGER (0..65535)
ACCESS read-only
STATUS optional
DESCRIPTION
        " "
::= { outlet1PDU10 6 }

switch2PDU10 OBJECT-TYPE
SYNTAX INTEGER (0..3)
ACCESS read-write
STATUS optional
DESCRIPTION
        " "
::= { outlet2PDU10 1 }

voltage2PDU10 OBJECT-TYPE
SYNTAX INTEGER (0..65535)
ACCESS read-only
STATUS optional
DESCRIPTION
        " "
::= { outlet2PDU10 2 }

current2PDU10 OBJECT-TYPE
SYNTAX INTEGER (0..65535)
ACCESS read-only
STATUS optional
DESCRIPTION
        " "
::= { outlet2PDU10 3 }

power2PDU10 OBJECT-TYPE
SYNTAX INTEGER (0..65535)
ACCESS read-only
STATUS optional
DESCRIPTION
        " "
::= { outlet2PDU10 4 }

pf2PDU10 OBJECT-TYPE
SYNTAX INTEGER (0..65535)
ACCESS read-only
STATUS optional
DESCRIPTION
        " "
::= { outlet2PDU10 5 }

energy2PDU10 OBJECT-TYPE
SYNTAX INTEGER (0..65535)
ACCESS read-only
STATUS optional
DESCRIPTION
        " "
::= { outlet2PDU10 6 }

switch3PDU10 OBJECT-TYPE
SYNTAX INTEGER (0..3)
ACCESS read-write
STATUS optional
DESCRIPTION
        " "
::= { outlet3PDU10 1 }

voltage3PDU10 OBJECT-TYPE
SYNTAX INTEGER (0..65535)
ACCESS read-only
STATUS optional
DESCRIPTION
        " "
::= { outlet3PDU10 2 }

current3PDU10 OBJECT-TYPE
SYNTAX INTEGER (0..65535)
ACCESS read-only
STATUS optional
DESCRIPTION
        " "
::= { outlet3PDU10 3 }

power3PDU10 OBJECT-TYPE
SYNTAX INTEGER (0..65535)
ACCESS read-only
STATUS optional
DESCRIPTION
        " "
::= { outlet3PDU10 4 }

pf3PDU10 OBJECT-TYPE
SYNTAX INTEGER (0..65535)
ACCESS read-only
STATUS optional
DESCRIPTION
        " "
::= { outlet3PDU10 5 }

energy3PDU10 OBJECT-TYPE
SYNTAX INTEGER (0..65535)
ACCESS read-only
STATUS optional
DESCRIPTION
        " "
::= { outlet3PDU10 6 }

switch4PDU10 OBJECT-TYPE
SYNTAX INTEGER (0..3)
ACCESS read-write
STATUS optional
DESCRIPTION
        " "
::= { outlet4PDU10 1 }

voltage4PDU10 OBJECT-TYPE
SYNTAX INTEGER (0..65535)
ACCESS read-only
STATUS optional
DESCRIPTION
        " "
::= { outlet4PDU10 2 }

current4PDU10 OBJECT-TYPE
SYNTAX INTEGER (0..65535)
ACCESS read-only
STATUS optional
DESCRIPTION
        " "
::= { outlet4PDU10 3 }

power4PDU10 OBJECT-TYPE
SYNTAX INTEGER (0..65535)
ACCESS read-only
STATUS optional
DESCRIPTION
        " "
::= { outlet4PDU10 4 }

pf4PDU10 OBJECT-TYPE
SYNTAX INTEGER (0..65535)
ACCESS read-only
STATUS optional
DESCRIPTION
        " "
::= { outlet4PDU10 5 }

energy4PDU10 OBJECT-TYPE
SYNTAX INTEGER (0..65535)
ACCESS read-only
STATUS optional
DESCRIPTION
        " "
::= { outlet4PDU10 6 }

switch5PDU10 OBJECT-TYPE
SYNTAX INTEGER (0..3)
ACCESS read-write
STATUS optional
DESCRIPTION
        " "
::= { outlet5PDU10 1 }

voltage5PDU10 OBJECT-TYPE
SYNTAX INTEGER (0..65535)
ACCESS read-only
STATUS optional
DESCRIPTION
        " "
::= { outlet5PDU10 2 }

current5PDU10 OBJECT-TYPE
SYNTAX INTEGER (0..65535)
ACCESS read-only
STATUS optional
DESCRIPTION
        " "
::= { outlet5PDU10 3 }

power5PDU10 OBJECT-TYPE
SYNTAX INTEGER (0..65535)
ACCESS read-only
STATUS optional
DESCRIPTION
        " "
::= { outlet5PDU10 4 }

pf5PDU10 OBJECT-TYPE
SYNTAX INTEGER (0..65535)
ACCESS read-only
STATUS optional
DESCRIPTION
        " "
::= { outlet5PDU10 5 }

energy5PDU10 OBJECT-TYPE
SYNTAX INTEGER (0..65535)
ACCESS read-only
STATUS optional
DESCRIPTION
        " "
::= { outlet5PDU10 6 }

switch6PDU10 OBJECT-TYPE
SYNTAX INTEGER (0..3)
ACCESS read-write
STATUS optional
DESCRIPTION
        " "
::= { outlet6PDU10 1 }

voltage6PDU10 OBJECT-TYPE
SYNTAX INTEGER (0..65535)
ACCESS read-only
STATUS optional
DESCRIPTION
        " "
::= { outlet6PDU10 2 }

current6PDU10 OBJECT-TYPE
SYNTAX INTEGER (0..65535)
ACCESS read-only
STATUS optional
DESCRIPTION
        " "
::= { outlet6PDU10 3 }

power6PDU10 OBJECT-TYPE
SYNTAX INTEGER (0..65535)
ACCESS read-only
STATUS optional
DESCRIPTION
        " "
::= { outlet6PDU10 4 }

pf6PDU10 OBJECT-TYPE
SYNTAX INTEGER (0..65535)
ACCESS read-only
STATUS optional
DESCRIPTION
        " "
::= { outlet6PDU10 5 }

energy6PDU10 OBJECT-TYPE
SYNTAX INTEGER (0..65535)
ACCESS read-only
STATUS optional
DESCRIPTION
        " "
::= { outlet6PDU10 6 }

switch7PDU10 OBJECT-TYPE
SYNTAX INTEGER (0..3)
ACCESS read-write
STATUS optional
DESCRIPTION
        " "
::= { outlet7PDU10 1 }

voltage7PDU10 OBJECT-TYPE
SYNTAX INTEGER (0..65535)
ACCESS read-only
STATUS optional
DESCRIPTION
        " "
::= { outlet7PDU10 2 }

current7PDU10 OBJECT-TYPE
SYNTAX INTEGER (0..65535)
ACCESS read-only
STATUS optional
DESCRIPTION
        " "
::= { outlet7PDU10 3 }

power7PDU10 OBJECT-TYPE
SYNTAX INTEGER (0..65535)
ACCESS read-only
STATUS optional
DESCRIPTION
        " "
::= { outlet7PDU10 4 }

pf7PDU10 OBJECT-TYPE
SYNTAX INTEGER (0..65535)
ACCESS read-only
STATUS optional
DESCRIPTION
        " "
::= { outlet7PDU10 5 }

energy7PDU10 OBJECT-TYPE
SYNTAX INTEGER (0..65535)
ACCESS read-only
STATUS optional
DESCRIPTION
        " "
::= { outlet7PDU10 6 }

switch8PDU10 OBJECT-TYPE
SYNTAX INTEGER (0..3)
ACCESS read-write
STATUS optional
DESCRIPTION
        " "
::= { outlet8PDU10 1 }

voltage8PDU10 OBJECT-TYPE
SYNTAX INTEGER (0..65535)
ACCESS read-only
STATUS optional
DESCRIPTION
        " "
::= { outlet8PDU10 2 }

current8PDU10 OBJECT-TYPE
SYNTAX INTEGER (0..65535)
ACCESS read-only
STATUS optional
DESCRIPTION
        " "
::= { outlet8PDU10 3 }

power8PDU10 OBJECT-TYPE
SYNTAX INTEGER (0..65535)
ACCESS read-only
STATUS optional
DESCRIPTION
        " "
::= { outlet8PDU10 4 }

pf8PDU10 OBJECT-TYPE
SYNTAX INTEGER (0..65535)
ACCESS read-only
STATUS optional
DESCRIPTION
        " "
::= { outlet8PDU10 5 }

energy8PDU10 OBJECT-TYPE
SYNTAX INTEGER (0..65535)
ACCESS read-only
STATUS optional
DESCRIPTION
        " "
::= { outlet8PDU10 6 }

switch9PDU10 OBJECT-TYPE
SYNTAX INTEGER (0..3)
ACCESS read-write
STATUS optional
DESCRIPTION
        " "
::= { outlet9PDU10 1 }

voltage9PDU10 OBJECT-TYPE
SYNTAX INTEGER (0..65535)
ACCESS read-only
STATUS optional
DESCRIPTION
        " "
::= { outlet9PDU10 2 }

current9PDU10 OBJECT-TYPE
SYNTAX INTEGER (0..65535)
ACCESS read-only
STATUS optional
DESCRIPTION
        " "
::= { outlet9PDU10 3 }

power9PDU10 OBJECT-TYPE
SYNTAX INTEGER (0..65535)
ACCESS read-only
STATUS optional
DESCRIPTION
        " "
::= { outlet9PDU10 4 }

pf9PDU10 OBJECT-TYPE
SYNTAX INTEGER (0..65535)
ACCESS read-only
STATUS optional
DESCRIPTION
        " "
::= { outlet9PDU10 5 }

energy9PDU10 OBJECT-TYPE
SYNTAX INTEGER (0..65535)
ACCESS read-only
STATUS optional
DESCRIPTION
        " "
::= { outlet9PDU10 6 }

switch10PDU10 OBJECT-TYPE
SYNTAX INTEGER (0..3)
ACCESS read-write
STATUS optional
DESCRIPTION
        " "
::= { outlet10PDU10 1 }

voltage10PDU10 OBJECT-TYPE
SYNTAX INTEGER (0..65535)
ACCESS read-only
STATUS optional
DESCRIPTION
        " "
::= { outlet10PDU10 2 }

current10PDU10 OBJECT-TYPE
SYNTAX INTEGER (0..65535)
ACCESS read-only
STATUS optional
DESCRIPTION
        " "
::= { outlet10PDU10 3 }

power10PDU10 OBJECT-TYPE
SYNTAX INTEGER (0..65535)
ACCESS read-only
STATUS optional
DESCRIPTION
        " "
::= { outlet10PDU10 4 }

pf10PDU10 OBJECT-TYPE
SYNTAX INTEGER (0..65535)
ACCESS read-only
STATUS optional
DESCRIPTION
        " "
::= { outlet10PDU10 5 }

energy10PDU10 OBJECT-TYPE
SYNTAX INTEGER (0..65535)
ACCESS read-only
STATUS optional
DESCRIPTION
        " "
::= { outlet10PDU10 6 }

switch11PDU10 OBJECT-TYPE
SYNTAX INTEGER (0..3)
ACCESS read-write
STATUS optional
DESCRIPTION
        " "
::= { outlet11PDU10 1 }

voltage11PDU10 OBJECT-TYPE
SYNTAX INTEGER (0..65535)
ACCESS read-only
STATUS optional
DESCRIPTION
        " "
::= { outlet11PDU10 2 }

current11PDU10 OBJECT-TYPE
SYNTAX INTEGER (0..65535)
ACCESS read-only
STATUS optional
DESCRIPTION
        " "
::= { outlet11PDU10 3 }

power11PDU10 OBJECT-TYPE
SYNTAX INTEGER (0..65535)
ACCESS read-only
STATUS optional
DESCRIPTION
        " "
::= { outlet11PDU10 4 }

pf11PDU10 OBJECT-TYPE
SYNTAX INTEGER (0..65535)
ACCESS read-only
STATUS optional
DESCRIPTION
        " "
::= { outlet11PDU10 5 }

energy11PDU10 OBJECT-TYPE
SYNTAX INTEGER (0..65535)
ACCESS read-only
STATUS optional
DESCRIPTION
        " "
::= { outlet11PDU10 6 }

switch12PDU10 OBJECT-TYPE
SYNTAX INTEGER (0..3)
ACCESS read-write
STATUS optional
DESCRIPTION
        " "
::= { outlet12PDU10 1 }

voltage12PDU10 OBJECT-TYPE
SYNTAX INTEGER (0..65535)
ACCESS read-only
STATUS optional
DESCRIPTION
        " "
::= { outlet12PDU10 2 }

current12PDU10 OBJECT-TYPE
SYNTAX INTEGER (0..65535)
ACCESS read-only
STATUS optional
DESCRIPTION
        " "
::= { outlet12PDU10 3 }

power12PDU10 OBJECT-TYPE
SYNTAX INTEGER (0..65535)
ACCESS read-only
STATUS optional
DESCRIPTION
        " "
::= { outlet12PDU10 4 }

pf12PDU10 OBJECT-TYPE
SYNTAX INTEGER (0..65535)
ACCESS read-only
STATUS optional
DESCRIPTION
        " "
::= { outlet12PDU10 5 }

energy12PDU10 OBJECT-TYPE
SYNTAX INTEGER (0..65535)
ACCESS read-only
STATUS optional
DESCRIPTION
        " "
::= { outlet12PDU10 6 }

switch13PDU10 OBJECT-TYPE
SYNTAX INTEGER (0..3)
ACCESS read-write
STATUS optional
DESCRIPTION
        " "
::= { outlet13PDU10 1 }

voltage13PDU10 OBJECT-TYPE
SYNTAX INTEGER (0..65535)
ACCESS read-only
STATUS optional
DESCRIPTION
        " "
::= { outlet13PDU10 2 }

current13PDU10 OBJECT-TYPE
SYNTAX INTEGER (0..65535)
ACCESS read-only
STATUS optional
DESCRIPTION
        " "
::= { outlet13PDU10 3 }

power13PDU10 OBJECT-TYPE
SYNTAX INTEGER (0..65535)
ACCESS read-only
STATUS optional
DESCRIPTION
        " "
::= { outlet13PDU10 4 }

pf13PDU10 OBJECT-TYPE
SYNTAX INTEGER (0..65535)
ACCESS read-only
STATUS optional
DESCRIPTION
        " "
::= { outlet13PDU10 5 }

energy13PDU10 OBJECT-TYPE
SYNTAX INTEGER (0..65535)
ACCESS read-only
STATUS optional
DESCRIPTION
        " "
::= { outlet13PDU10 6 }

switch14PDU10 OBJECT-TYPE
SYNTAX INTEGER (0..3)
ACCESS read-write
STATUS optional
DESCRIPTION
        " "
::= { outlet14PDU10 1 }

voltage14PDU10 OBJECT-TYPE
SYNTAX INTEGER (0..65535)
ACCESS read-only
STATUS optional
DESCRIPTION
        " "
::= { outlet14PDU10 2 }

current14PDU10 OBJECT-TYPE
SYNTAX INTEGER (0..65535)
ACCESS read-only
STATUS optional
DESCRIPTION
        " "
::= { outlet14PDU10 3 }

power14PDU10 OBJECT-TYPE
SYNTAX INTEGER (0..65535)
ACCESS read-only
STATUS optional
DESCRIPTION
        " "
::= { outlet14PDU10 4 }

pf14PDU10 OBJECT-TYPE
SYNTAX INTEGER (0..65535)
ACCESS read-only
STATUS optional
DESCRIPTION
        " "
::= { outlet14PDU10 5 }

energy14PDU10 OBJECT-TYPE
SYNTAX INTEGER (0..65535)
ACCESS read-only
STATUS optional
DESCRIPTION
        " "
::= { outlet14PDU10 6 }

switch15PDU10 OBJECT-TYPE
SYNTAX INTEGER (0..3)
ACCESS read-write
STATUS optional
DESCRIPTION
        " "
::= { outlet15PDU10 1 }

voltage15PDU10 OBJECT-TYPE
SYNTAX INTEGER (0..65535)
ACCESS read-only
STATUS optional
DESCRIPTION
        " "
::= { outlet15PDU10 2 }

current15PDU10 OBJECT-TYPE
SYNTAX INTEGER (0..65535)
ACCESS read-only
STATUS optional
DESCRIPTION
        " "
::= { outlet15PDU10 3 }

power15PDU10 OBJECT-TYPE
SYNTAX INTEGER (0..65535)
ACCESS read-only
STATUS optional
DESCRIPTION
        " "
::= { outlet15PDU10 4 }

pf15PDU10 OBJECT-TYPE
SYNTAX INTEGER (0..65535)
ACCESS read-only
STATUS optional
DESCRIPTION
        " "
::= { outlet15PDU10 5 }

energy15PDU10 OBJECT-TYPE
SYNTAX INTEGER (0..65535)
ACCESS read-only
STATUS optional
DESCRIPTION
        " "
::= { outlet15PDU10 6 }

switch16PDU10 OBJECT-TYPE
SYNTAX INTEGER (0..3)
ACCESS read-write
STATUS optional
DESCRIPTION
        " "
::= { outlet16PDU10 1 }

voltage16PDU10 OBJECT-TYPE
SYNTAX INTEGER (0..65535)
ACCESS read-only
STATUS optional
DESCRIPTION
        " "
::= { outlet16PDU10 2 }

current16PDU10 OBJECT-TYPE
SYNTAX INTEGER (0..65535)
ACCESS read-only
STATUS optional
DESCRIPTION
        " "
::= { outlet16PDU10 3 }

power16PDU10 OBJECT-TYPE
SYNTAX INTEGER (0..65535)
ACCESS read-only
STATUS optional
DESCRIPTION
        " "
::= { outlet16PDU10 4 }

pf16PDU10 OBJECT-TYPE
SYNTAX INTEGER (0..65535)
ACCESS read-only
STATUS optional
DESCRIPTION
        " "
::= { outlet16PDU10 5 }

energy16PDU10 OBJECT-TYPE
SYNTAX INTEGER (0..65535)
ACCESS read-only
STATUS optional
DESCRIPTION
        " "
::= { outlet16PDU10 6 }

switch17PDU10 OBJECT-TYPE
SYNTAX INTEGER (0..3)
ACCESS read-write
STATUS optional
DESCRIPTION
        " "
::= { outlet17PDU10 1 }

voltage17PDU10 OBJECT-TYPE
SYNTAX INTEGER (0..65535)
ACCESS read-only
STATUS optional
DESCRIPTION
        " "
::= { outlet17PDU10 2 }

current17PDU10 OBJECT-TYPE
SYNTAX INTEGER (0..65535)
ACCESS read-only
STATUS optional
DESCRIPTION
        " "
::= { outlet17PDU10 3 }

power17PDU10 OBJECT-TYPE
SYNTAX INTEGER (0..65535)
ACCESS read-only
STATUS optional
DESCRIPTION
        " "
::= { outlet17PDU10 4 }

pf17PDU10 OBJECT-TYPE
SYNTAX INTEGER (0..65535)
ACCESS read-only
STATUS optional
DESCRIPTION
        " "
::= { outlet17PDU10 5 }

energy17PDU10 OBJECT-TYPE
SYNTAX INTEGER (0..65535)
ACCESS read-only
STATUS optional
DESCRIPTION
        " "
::= { outlet17PDU10 6 }

switch18PDU10 OBJECT-TYPE
SYNTAX INTEGER (0..3)
ACCESS read-write
STATUS optional
DESCRIPTION
        " "
::= { outlet18PDU10 1 }

voltage18PDU10 OBJECT-TYPE
SYNTAX INTEGER (0..65535)
ACCESS read-only
STATUS optional
DESCRIPTION
        " "
::= { outlet18PDU10 2 }

current18PDU10 OBJECT-TYPE
SYNTAX INTEGER (0..65535)
ACCESS read-only
STATUS optional
DESCRIPTION
        " "
::= { outlet18PDU10 3 }

power18PDU10 OBJECT-TYPE
SYNTAX INTEGER (0..65535)
ACCESS read-only
STATUS optional
DESCRIPTION
        " "
::= { outlet18PDU10 4 }

pf18PDU10 OBJECT-TYPE
SYNTAX INTEGER (0..65535)
ACCESS read-only
STATUS optional
DESCRIPTION
        " "
::= { outlet18PDU10 5 }

energy18PDU10 OBJECT-TYPE
SYNTAX INTEGER (0..65535)
ACCESS read-only
STATUS optional
DESCRIPTION
        " "
::= { outlet18PDU10 6 }

switch19PDU10 OBJECT-TYPE
SYNTAX INTEGER (0..3)
ACCESS read-write
STATUS optional
DESCRIPTION
        " "
::= { outlet19PDU10 1 }

voltage19PDU10 OBJECT-TYPE
SYNTAX INTEGER (0..65535)
ACCESS read-only
STATUS optional
DESCRIPTION
        " "
::= { outlet19PDU10 2 }

current19PDU10 OBJECT-TYPE
SYNTAX INTEGER (0..65535)
ACCESS read-only
STATUS optional
DESCRIPTION
        " "
::= { outlet19PDU10 3 }

power19PDU10 OBJECT-TYPE
SYNTAX INTEGER (0..65535)
ACCESS read-only
STATUS optional
DESCRIPTION
        " "
::= { outlet19PDU10 4 }

pf19PDU10 OBJECT-TYPE
SYNTAX INTEGER (0..65535)
ACCESS read-only
STATUS optional
DESCRIPTION
        " "
::= { outlet19PDU10 5 }

energy19PDU10 OBJECT-TYPE
SYNTAX INTEGER (0..65535)
ACCESS read-only
STATUS optional
DESCRIPTION
        " "
::= { outlet19PDU10 6 }

switch20PDU10 OBJECT-TYPE
SYNTAX INTEGER (0..3)
ACCESS read-write
STATUS optional
DESCRIPTION
        " "
::= { outlet20PDU10 1 }

voltage20PDU10 OBJECT-TYPE
SYNTAX INTEGER (0..65535)
ACCESS read-only
STATUS optional
DESCRIPTION
        " "
::= { outlet20PDU10 2 }

current20PDU10 OBJECT-TYPE
SYNTAX INTEGER (0..65535)
ACCESS read-only
STATUS optional
DESCRIPTION
        " "
::= { outlet20PDU10 3 }

power20PDU10 OBJECT-TYPE
SYNTAX INTEGER (0..65535)
ACCESS read-only
STATUS optional
DESCRIPTION
        " "
::= { outlet20PDU10 4 }

pf20PDU10 OBJECT-TYPE
SYNTAX INTEGER (0..65535)
ACCESS read-only
STATUS optional
DESCRIPTION
        " "
::= { outlet20PDU10 5 }

energy20PDU10 OBJECT-TYPE
SYNTAX INTEGER (0..65535)
ACCESS read-only
STATUS optional
DESCRIPTION
        " "
::= { outlet20PDU10 6 }

switch21PDU10 OBJECT-TYPE
SYNTAX INTEGER (0..3)
ACCESS read-write
STATUS optional
DESCRIPTION
        " "
::= { outlet21PDU10 1 }

voltage21PDU10 OBJECT-TYPE
SYNTAX INTEGER (0..65535)
ACCESS read-only
STATUS optional
DESCRIPTION
        " "
::= { outlet21PDU10 2 }

current21PDU10 OBJECT-TYPE
SYNTAX INTEGER (0..65535)
ACCESS read-only
STATUS optional
DESCRIPTION
        " "
::= { outlet21PDU10 3 }

power21PDU10 OBJECT-TYPE
SYNTAX INTEGER (0..65535)
ACCESS read-only
STATUS optional
DESCRIPTION
        " "
::= { outlet21PDU10 4 }

pf21PDU10 OBJECT-TYPE
SYNTAX INTEGER (0..65535)
ACCESS read-only
STATUS optional
DESCRIPTION
        " "
::= { outlet21PDU10 5 }

energy21PDU10 OBJECT-TYPE
SYNTAX INTEGER (0..65535)
ACCESS read-only
STATUS optional
DESCRIPTION
        " "
::= { outlet21PDU10 6 }

switch22PDU10 OBJECT-TYPE
SYNTAX INTEGER (0..3)
ACCESS read-write
STATUS optional
DESCRIPTION
        " "
::= { outlet22PDU10 1 }

voltage22PDU10 OBJECT-TYPE
SYNTAX INTEGER (0..65535)
ACCESS read-only
STATUS optional
DESCRIPTION
        " "
::= { outlet22PDU10 2 }

current22PDU10 OBJECT-TYPE
SYNTAX INTEGER (0..65535)
ACCESS read-only
STATUS optional
DESCRIPTION
        " "
::= { outlet22PDU10 3 }

power22PDU10 OBJECT-TYPE
SYNTAX INTEGER (0..65535)
ACCESS read-only
STATUS optional
DESCRIPTION
        " "
::= { outlet22PDU10 4 }

pf22PDU10 OBJECT-TYPE
SYNTAX INTEGER (0..65535)
ACCESS read-only
STATUS optional
DESCRIPTION
        " "
::= { outlet22PDU10 5 }

energy22PDU10 OBJECT-TYPE
SYNTAX INTEGER (0..65535)
ACCESS read-only
STATUS optional
DESCRIPTION
        " "
::= { outlet22PDU10 6 }

switch23PDU10 OBJECT-TYPE
SYNTAX INTEGER (0..3)
ACCESS read-write
STATUS optional
DESCRIPTION
        " "
::= { outlet23PDU10 1 }

voltage23PDU10 OBJECT-TYPE
SYNTAX INTEGER (0..65535)
ACCESS read-only
STATUS optional
DESCRIPTION
        " "
::= { outlet23PDU10 2 }

current23PDU10 OBJECT-TYPE
SYNTAX INTEGER (0..65535)
ACCESS read-only
STATUS optional
DESCRIPTION
        " "
::= { outlet23PDU10 3 }

power23PDU10 OBJECT-TYPE
SYNTAX INTEGER (0..65535)
ACCESS read-only
STATUS optional
DESCRIPTION
        " "
::= { outlet23PDU10 4 }

pf23PDU10 OBJECT-TYPE
SYNTAX INTEGER (0..65535)
ACCESS read-only
STATUS optional
DESCRIPTION
        " "
::= { outlet23PDU10 5 }

energy23PDU10 OBJECT-TYPE
SYNTAX INTEGER (0..65535)
ACCESS read-only
STATUS optional
DESCRIPTION
        " "
::= { outlet23PDU10 6 }

switch24PDU10 OBJECT-TYPE
SYNTAX INTEGER (0..3)
ACCESS read-write
STATUS optional
DESCRIPTION
        " "
::= { outlet24PDU10 1 }

voltage24PDU10 OBJECT-TYPE
SYNTAX INTEGER (0..65535)
ACCESS read-only
STATUS optional
DESCRIPTION
        " "
::= { outlet24PDU10 2 }

current24PDU10 OBJECT-TYPE
SYNTAX INTEGER (0..65535)
ACCESS read-only
STATUS optional
DESCRIPTION
        " "
::= { outlet24PDU10 3 }

power24PDU10 OBJECT-TYPE
SYNTAX INTEGER (0..65535)
ACCESS read-only
STATUS optional
DESCRIPTION
        " "
::= { outlet24PDU10 4 }

pf24PDU10 OBJECT-TYPE
SYNTAX INTEGER (0..65535)
ACCESS read-only
STATUS optional
DESCRIPTION
        " "
::= { outlet24PDU10 5 }

energy24PDU10 OBJECT-TYPE
SYNTAX INTEGER (0..65535)
ACCESS read-only
STATUS optional
DESCRIPTION
        " "
::= { outlet24PDU10 6 }

switch25PDU10 OBJECT-TYPE
SYNTAX INTEGER (0..3)
ACCESS read-write
STATUS optional
DESCRIPTION
        " "
::= { outlet25PDU10 1 }

voltage25PDU10 OBJECT-TYPE
SYNTAX INTEGER (0..65535)
ACCESS read-only
STATUS optional
DESCRIPTION
        " "
::= { outlet25PDU10 2 }

current25PDU10 OBJECT-TYPE
SYNTAX INTEGER (0..65535)
ACCESS read-only
STATUS optional
DESCRIPTION
        " "
::= { outlet25PDU10 3 }

power25PDU10 OBJECT-TYPE
SYNTAX INTEGER (0..65535)
ACCESS read-only
STATUS optional
DESCRIPTION
        " "
::= { outlet25PDU10 4 }

pf25PDU10 OBJECT-TYPE
SYNTAX INTEGER (0..65535)
ACCESS read-only
STATUS optional
DESCRIPTION
        " "
::= { outlet25PDU10 5 }

energy25PDU10 OBJECT-TYPE
SYNTAX INTEGER (0..65535)
ACCESS read-only
STATUS optional
DESCRIPTION
        " "
::= { outlet25PDU10 6 }

switch26PDU10 OBJECT-TYPE
SYNTAX INTEGER (0..3)
ACCESS read-write
STATUS optional
DESCRIPTION
        " "
::= { outlet26PDU10 1 }

voltage26PDU10 OBJECT-TYPE
SYNTAX INTEGER (0..65535)
ACCESS read-only
STATUS optional
DESCRIPTION
        " "
::= { outlet26PDU10 2 }

current26PDU10 OBJECT-TYPE
SYNTAX INTEGER (0..65535)
ACCESS read-only
STATUS optional
DESCRIPTION
        " "
::= { outlet26PDU10 3 }

power26PDU10 OBJECT-TYPE
SYNTAX INTEGER (0..65535)
ACCESS read-only
STATUS optional
DESCRIPTION
        " "
::= { outlet26PDU10 4 }

pf26PDU10 OBJECT-TYPE
SYNTAX INTEGER (0..65535)
ACCESS read-only
STATUS optional
DESCRIPTION
        " "
::= { outlet26PDU10 5 }

energy26PDU10 OBJECT-TYPE
SYNTAX INTEGER (0..65535)
ACCESS read-only
STATUS optional
DESCRIPTION
        " "
::= { outlet26PDU10 6 }

switch27PDU10 OBJECT-TYPE
SYNTAX INTEGER (0..3)
ACCESS read-write
STATUS optional
DESCRIPTION
        " "
::= { outlet27PDU10 1 }

voltage27PDU10 OBJECT-TYPE
SYNTAX INTEGER (0..65535)
ACCESS read-only
STATUS optional
DESCRIPTION
        " "
::= { outlet27PDU10 2 }

current27PDU10 OBJECT-TYPE
SYNTAX INTEGER (0..65535)
ACCESS read-only
STATUS optional
DESCRIPTION
        " "
::= { outlet27PDU10 3 }

power27PDU10 OBJECT-TYPE
SYNTAX INTEGER (0..65535)
ACCESS read-only
STATUS optional
DESCRIPTION
        " "
::= { outlet27PDU10 4 }

pf27PDU10 OBJECT-TYPE
SYNTAX INTEGER (0..65535)
ACCESS read-only
STATUS optional
DESCRIPTION
        " "
::= { outlet27PDU10 5 }

energy27PDU10 OBJECT-TYPE
SYNTAX INTEGER (0..65535)
ACCESS read-only
STATUS optional
DESCRIPTION
        " "
::= { outlet27PDU10 6 }

switch28PDU10 OBJECT-TYPE
SYNTAX INTEGER (0..3)
ACCESS read-write
STATUS optional
DESCRIPTION
        " "
::= { outlet28PDU10 1 }

voltage28PDU10 OBJECT-TYPE
SYNTAX INTEGER (0..65535)
ACCESS read-only
STATUS optional
DESCRIPTION
        " "
::= { outlet28PDU10 2 }

current28PDU10 OBJECT-TYPE
SYNTAX INTEGER (0..65535)
ACCESS read-only
STATUS optional
DESCRIPTION
        " "
::= { outlet28PDU10 3 }

power28PDU10 OBJECT-TYPE
SYNTAX INTEGER (0..65535)
ACCESS read-only
STATUS optional
DESCRIPTION
        " "
::= { outlet28PDU10 4 }

pf28PDU10 OBJECT-TYPE
SYNTAX INTEGER (0..65535)
ACCESS read-only
STATUS optional
DESCRIPTION
        " "
::= { outlet28PDU10 5 }

energy28PDU10 OBJECT-TYPE
SYNTAX INTEGER (0..65535)
ACCESS read-only
STATUS optional
DESCRIPTION
        " "
::= { outlet28PDU10 6 }

switch29PDU10 OBJECT-TYPE
SYNTAX INTEGER (0..3)
ACCESS read-write
STATUS optional
DESCRIPTION
        " "
::= { outlet29PDU10 1 }

voltage29PDU10 OBJECT-TYPE
SYNTAX INTEGER (0..65535)
ACCESS read-only
STATUS optional
DESCRIPTION
        " "
::= { outlet29PDU10 2 }

current29PDU10 OBJECT-TYPE
SYNTAX INTEGER (0..65535)
ACCESS read-only
STATUS optional
DESCRIPTION
        " "
::= { outlet29PDU10 3 }

power29PDU10 OBJECT-TYPE
SYNTAX INTEGER (0..65535)
ACCESS read-only
STATUS optional
DESCRIPTION
        " "
::= { outlet29PDU10 4 }

pf29PDU10 OBJECT-TYPE
SYNTAX INTEGER (0..65535)
ACCESS read-only
STATUS optional
DESCRIPTION
        " "
::= { outlet29PDU10 5 }

energy29PDU10 OBJECT-TYPE
SYNTAX INTEGER (0..65535)
ACCESS read-only
STATUS optional
DESCRIPTION
        " "
::= { outlet29PDU10 6 }

switch30PDU10 OBJECT-TYPE
SYNTAX INTEGER (0..3)
ACCESS read-write
STATUS optional
DESCRIPTION
        " "
::= { outlet30PDU10 1 }

voltage30PDU10 OBJECT-TYPE
SYNTAX INTEGER (0..65535)
ACCESS read-only
STATUS optional
DESCRIPTION
        " "
::= { outlet30PDU10 2 }

current30PDU10 OBJECT-TYPE
SYNTAX INTEGER (0..65535)
ACCESS read-only
STATUS optional
DESCRIPTION
        " "
::= { outlet30PDU10 3 }

power30PDU10 OBJECT-TYPE
SYNTAX INTEGER (0..65535)
ACCESS read-only
STATUS optional
DESCRIPTION
        " "
::= { outlet30PDU10 4 }

pf30PDU10 OBJECT-TYPE
SYNTAX INTEGER (0..65535)
ACCESS read-only
STATUS optional
DESCRIPTION
        " "
::= { outlet30PDU10 5 }

energy30PDU10 OBJECT-TYPE
SYNTAX INTEGER (0..65535)
ACCESS read-only
STATUS optional
DESCRIPTION
        " "
::= { outlet30PDU10 6 }

switch31PDU10 OBJECT-TYPE
SYNTAX INTEGER (0..3)
ACCESS read-write
STATUS optional
DESCRIPTION
        " "
::= { outlet31PDU10 1 }

voltage31PDU10 OBJECT-TYPE
SYNTAX INTEGER (0..65535)
ACCESS read-only
STATUS optional
DESCRIPTION
        " "
::= { outlet31PDU10 2 }

current31PDU10 OBJECT-TYPE
SYNTAX INTEGER (0..65535)
ACCESS read-only
STATUS optional
DESCRIPTION
        " "
::= { outlet31PDU10 3 }

power31PDU10 OBJECT-TYPE
SYNTAX INTEGER (0..65535)
ACCESS read-only
STATUS optional
DESCRIPTION
        " "
::= { outlet31PDU10 4 }

pf31PDU10 OBJECT-TYPE
SYNTAX INTEGER (0..65535)
ACCESS read-only
STATUS optional
DESCRIPTION
        " "
::= { outlet31PDU10 5 }

energy31PDU10 OBJECT-TYPE
SYNTAX INTEGER (0..65535)
ACCESS read-only
STATUS optional
DESCRIPTION
        " "
::= { outlet31PDU10 6 }

switch32PDU10 OBJECT-TYPE
SYNTAX INTEGER (0..3)
ACCESS read-write
STATUS optional
DESCRIPTION
        " "
::= { outlet32PDU10 1 }

voltage32PDU10 OBJECT-TYPE
SYNTAX INTEGER (0..65535)
ACCESS read-only
STATUS optional
DESCRIPTION
        " "
::= { outlet32PDU10 2 }

current32PDU10 OBJECT-TYPE
SYNTAX INTEGER (0..65535)
ACCESS read-only
STATUS optional
DESCRIPTION
        " "
::= { outlet32PDU10 3 }

power32PDU10 OBJECT-TYPE
SYNTAX INTEGER (0..65535)
ACCESS read-only
STATUS optional
DESCRIPTION
        " "
::= { outlet32PDU10 4 }

pf32PDU10 OBJECT-TYPE
SYNTAX INTEGER (0..65535)
ACCESS read-only
STATUS optional
DESCRIPTION
        " "
::= { outlet32PDU10 5 }

energy32PDU10 OBJECT-TYPE
SYNTAX INTEGER (0..65535)
ACCESS read-only
STATUS optional
DESCRIPTION
        " "
::= { outlet32PDU10 6 }

switch33PDU10 OBJECT-TYPE
SYNTAX INTEGER (0..3)
ACCESS read-write
STATUS optional
DESCRIPTION
        " "
::= { outlet33PDU10 1 }

voltage33PDU10 OBJECT-TYPE
SYNTAX INTEGER (0..65535)
ACCESS read-only
STATUS optional
DESCRIPTION
        " "
::= { outlet33PDU10 2 }

current33PDU10 OBJECT-TYPE
SYNTAX INTEGER (0..65535)
ACCESS read-only
STATUS optional
DESCRIPTION
        " "
::= { outlet33PDU10 3 }

power33PDU10 OBJECT-TYPE
SYNTAX INTEGER (0..65535)
ACCESS read-only
STATUS optional
DESCRIPTION
        " "
::= { outlet33PDU10 4 }

pf33PDU10 OBJECT-TYPE
SYNTAX INTEGER (0..65535)
ACCESS read-only
STATUS optional
DESCRIPTION
        " "
::= { outlet33PDU10 5 }

energy33PDU10 OBJECT-TYPE
SYNTAX INTEGER (0..65535)
ACCESS read-only
STATUS optional
DESCRIPTION
        " "
::= { outlet33PDU10 6 }

switch34PDU10 OBJECT-TYPE
SYNTAX INTEGER (0..3)
ACCESS read-write
STATUS optional
DESCRIPTION
        " "
::= { outlet34PDU10 1 }

voltage34PDU10 OBJECT-TYPE
SYNTAX INTEGER (0..65535)
ACCESS read-only
STATUS optional
DESCRIPTION
        " "
::= { outlet34PDU10 2 }

current34PDU10 OBJECT-TYPE
SYNTAX INTEGER (0..65535)
ACCESS read-only
STATUS optional
DESCRIPTION
        " "
::= { outlet34PDU10 3 }

power34PDU10 OBJECT-TYPE
SYNTAX INTEGER (0..65535)
ACCESS read-only
STATUS optional
DESCRIPTION
        " "
::= { outlet34PDU10 4 }

pf34PDU10 OBJECT-TYPE
SYNTAX INTEGER (0..65535)
ACCESS read-only
STATUS optional
DESCRIPTION
        " "
::= { outlet34PDU10 5 }

energy34PDU10 OBJECT-TYPE
SYNTAX INTEGER (0..65535)
ACCESS read-only
STATUS optional
DESCRIPTION
        " "
::= { outlet34PDU10 6 }

switch35PDU10 OBJECT-TYPE
SYNTAX INTEGER (0..3)
ACCESS read-write
STATUS optional
DESCRIPTION
        " "
::= { outlet35PDU10 1 }

voltage35PDU10 OBJECT-TYPE
SYNTAX INTEGER (0..65535)
ACCESS read-only
STATUS optional
DESCRIPTION
        " "
::= { outlet35PDU10 2 }

current35PDU10 OBJECT-TYPE
SYNTAX INTEGER (0..65535)
ACCESS read-only
STATUS optional
DESCRIPTION
        " "
::= { outlet35PDU10 3 }

power35PDU10 OBJECT-TYPE
SYNTAX INTEGER (0..65535)
ACCESS read-only
STATUS optional
DESCRIPTION
        " "
::= { outlet35PDU10 4 }

pf35PDU10 OBJECT-TYPE
SYNTAX INTEGER (0..65535)
ACCESS read-only
STATUS optional
DESCRIPTION
        " "
::= { outlet35PDU10 5 }

energy35PDU10 OBJECT-TYPE
SYNTAX INTEGER (0..65535)
ACCESS read-only
STATUS optional
DESCRIPTION
        " "
::= { outlet35PDU10 6 }

switch36PDU10 OBJECT-TYPE
SYNTAX INTEGER (0..3)
ACCESS read-write
STATUS optional
DESCRIPTION
        " "
::= { outlet36PDU10 1 }

voltage36PDU10 OBJECT-TYPE
SYNTAX INTEGER (0..65535)
ACCESS read-only
STATUS optional
DESCRIPTION
        " "
::= { outlet36PDU10 2 }

current36PDU10 OBJECT-TYPE
SYNTAX INTEGER (0..65535)
ACCESS read-only
STATUS optional
DESCRIPTION
        " "
::= { outlet36PDU10 3 }

power36PDU10 OBJECT-TYPE
SYNTAX INTEGER (0..65535)
ACCESS read-only
STATUS optional
DESCRIPTION
        " "
::= { outlet36PDU10 4 }

pf36PDU10 OBJECT-TYPE
SYNTAX INTEGER (0..65535)
ACCESS read-only
STATUS optional
DESCRIPTION
        " "
::= { outlet36PDU10 5 }

energy36PDU10 OBJECT-TYPE
SYNTAX INTEGER (0..65535)
ACCESS read-only
STATUS optional
DESCRIPTION
        " "
::= { outlet36PDU10 6 }

sensor1 OBJECT IDENTIFIER ::= { pdu10 4 }

temperature1PDU10 OBJECT-TYPE
SYNTAX INTEGER (0..65535)
ACCESS read-only
STATUS optional
DESCRIPTION
        " "
::= { sensor1 1 }

humidity1PDU10 OBJECT-TYPE
SYNTAX INTEGER (0..65535)
ACCESS read-only
STATUS optional
DESCRIPTION
        " "
::= { sensor1 2 }

temperature2PDU10 OBJECT-TYPE
SYNTAX INTEGER (0..65535)
ACCESS read-only
STATUS optional
DESCRIPTION
        " "
::= { sensor1 3 }

humidity2PDU10 OBJECT-TYPE
SYNTAX INTEGER (0..65535)
ACCESS read-only
STATUS optional
DESCRIPTION
        " "
::= { sensor1 4 }

inputStatus1PDU10 OBJECT-TYPE
SYNTAX INTEGER (0..1)
ACCESS read-only
STATUS optional
DESCRIPTION
        " "
::= { sensor1 5 }

inputStatus2PDU10 OBJECT-TYPE
SYNTAX INTEGER (0..1)
ACCESS read-only
STATUS optional
DESCRIPTION
        " "
::= { sensor1 6 }

inputStatus3PDU10 OBJECT-TYPE
SYNTAX INTEGER (0..1)
ACCESS read-only
STATUS optional
DESCRIPTION
        " "
::= { sensor1 7 }

inputStatus4PDU10 OBJECT-TYPE
SYNTAX INTEGER (0..1)
ACCESS read-only
STATUS optional
DESCRIPTION
        " "
::= { sensor1 8 }

doStatus1PDU10 OBJECT-TYPE
SYNTAX INTEGER (0..1)
ACCESS read-only
STATUS optional
DESCRIPTION
        " "
::= { sensor1 9 }

doStatus2PDU10 OBJECT-TYPE
SYNTAX INTEGER (0..1)
ACCESS read-only
STATUS optional
DESCRIPTION
        " "
::= { sensor1 10 }

baseinfo1 OBJECT IDENTIFIER ::= { pdu11 1 }

cascadeAlarmPDU11 OBJECT-TYPE
SYNTAX INTEGER (0..3)
ACCESS read-only
STATUS optional
DESCRIPTION
        " "
::= { baseinfo1 1 }

deviceNamePDU11 OBJECT-TYPE
SYNTAX DisplayString (SIZE (32))
ACCESS read-write
STATUS optional
DESCRIPTION
        " "
::= { baseinfo1 2 }

outletNumberPDU11 OBJECT-TYPE
SYNTAX INTEGER (0..36)
ACCESS read-only
STATUS optional
DESCRIPTION
        " "
::= { baseinfo1 3 }

temphum1WarnStatPDU11 OBJECT-TYPE
SYNTAX INTEGER (0..127)
ACCESS read-only
STATUS optional
DESCRIPTION
        " "
::= { baseinfo1 4 }

temphum2WarnStatPDU11 OBJECT-TYPE
SYNTAX INTEGER (0..127)
ACCESS read-only
STATUS optional
DESCRIPTION
        " "
::= { baseinfo1 5 }

input1WarnStatPDU11 OBJECT-TYPE
SYNTAX INTEGER (0..1)
ACCESS read-only
STATUS optional
DESCRIPTION
        " "
::= { baseinfo1 6 }

input2WarnStatPDU11 OBJECT-TYPE
SYNTAX INTEGER (0..1)
ACCESS read-only
STATUS optional
DESCRIPTION
        " "
::= { baseinfo1 7 }

input3WarnStatPDU11 OBJECT-TYPE
SYNTAX INTEGER (0..1)
ACCESS read-only
STATUS optional
DESCRIPTION
        " "
::= { baseinfo1 8 }

input4WarnStatPDU11 OBJECT-TYPE
SYNTAX INTEGER (0..1)
ACCESS read-only
STATUS optional
DESCRIPTION
        " "
::= { baseinfo1 9 }

currentL1WarnStatPDU11 OBJECT-TYPE
SYNTAX INTEGER (0..127)
ACCESS read-only
STATUS optional
DESCRIPTION
        " "
::= { baseinfo1 10 }

currentL2WarnStatPDU11 OBJECT-TYPE
SYNTAX INTEGER (0..127)
ACCESS read-only
STATUS optional
DESCRIPTION
        " "
::= { baseinfo1 11 }

currentL3WarnStatPDU11 OBJECT-TYPE
SYNTAX INTEGER (0..127)
ACCESS read-only
STATUS optional
DESCRIPTION
        " "
::= { baseinfo1 12 }

voltageL1WarnStatPDU11 OBJECT-TYPE
SYNTAX INTEGER (0..127)
ACCESS read-only
STATUS optional
DESCRIPTION
        " "
::= { baseinfo1 13 }

voltageL2WarnStatPDU11 OBJECT-TYPE
SYNTAX INTEGER (0..127)
ACCESS read-only
STATUS optional
DESCRIPTION
        " "
::= { baseinfo1 14 }

voltageL3WarnStatPDU11 OBJECT-TYPE
SYNTAX INTEGER (0..127)
ACCESS read-only
STATUS optional
DESCRIPTION
        " "
::= { baseinfo1 15 }

outlet1WarnStatPDU11 OBJECT-TYPE
SYNTAX INTEGER (0..127)
ACCESS read-only
STATUS optional
DESCRIPTION
        " "
::= { baseinfo1 16 }

outlet2WarnStatPDU11 OBJECT-TYPE
SYNTAX INTEGER (0..127)
ACCESS read-only
STATUS optional
DESCRIPTION
        " "
::= { baseinfo1 17 }

outlet3WarnStatPDU11 OBJECT-TYPE
SYNTAX INTEGER (0..127)
ACCESS read-only
STATUS optional
DESCRIPTION
        " "
::= { baseinfo1 18 }

outlet4WarnStatPDU11 OBJECT-TYPE
SYNTAX INTEGER (0..127)
ACCESS read-only
STATUS optional
DESCRIPTION
        " "
::= { baseinfo1 19 }

outlet5WarnStatPDU11 OBJECT-TYPE
SYNTAX INTEGER (0..127)
ACCESS read-only
STATUS optional
DESCRIPTION
        " "
::= { baseinfo1 20 }

outlet6WarnStatPDU11 OBJECT-TYPE
SYNTAX INTEGER (0..127)
ACCESS read-only
STATUS optional
DESCRIPTION
        " "
::= { baseinfo1 21 }

outlet7WarnStatPDU11 OBJECT-TYPE
SYNTAX INTEGER (0..127)
ACCESS read-only
STATUS optional
DESCRIPTION
        " "
::= { baseinfo1 22 }

outlet8WarnStatPDU11 OBJECT-TYPE
SYNTAX INTEGER (0..127)
ACCESS read-only
STATUS optional
DESCRIPTION
        " "
::= { baseinfo1 23 }

outlet9WarnStatPDU11 OBJECT-TYPE
SYNTAX INTEGER (0..127)
ACCESS read-only
STATUS optional
DESCRIPTION
        " "
::= { baseinfo1 24 }

outlet10WarnStatPDU11 OBJECT-TYPE
SYNTAX INTEGER (0..127)
ACCESS read-only
STATUS optional
DESCRIPTION
        " "
::= { baseinfo1 25 }

outlet11WarnStatPDU11 OBJECT-TYPE
SYNTAX INTEGER (0..127)
ACCESS read-only
STATUS optional
DESCRIPTION
        " "
::= { baseinfo1 26 }

outlet12WarnStatPDU11 OBJECT-TYPE
SYNTAX INTEGER (0..127)
ACCESS read-only
STATUS optional
DESCRIPTION
        " "
::= { baseinfo1 27 }

outlet13WarnStatPDU11 OBJECT-TYPE
SYNTAX INTEGER (0..127)
ACCESS read-only
STATUS optional
DESCRIPTION
        " "
::= { baseinfo1 28 }

outlet14WarnStatPDU11 OBJECT-TYPE
SYNTAX INTEGER (0..127)
ACCESS read-only
STATUS optional
DESCRIPTION
        " "
::= { baseinfo1 29 }

outlet15WarnStatPDU11 OBJECT-TYPE
SYNTAX INTEGER (0..127)
ACCESS read-only
STATUS optional
DESCRIPTION
        " "
::= { baseinfo1 30 }

outlet16WarnStatPDU11 OBJECT-TYPE
SYNTAX INTEGER (0..127)
ACCESS read-only
STATUS optional
DESCRIPTION
        " "
::= { baseinfo1 31 }

outlet17WarnStatPDU11 OBJECT-TYPE
SYNTAX INTEGER (0..127)
ACCESS read-only
STATUS optional
DESCRIPTION
        " "
::= { baseinfo1 32 }

outlet18WarnStatPDU11 OBJECT-TYPE
SYNTAX INTEGER (0..127)
ACCESS read-only
STATUS optional
DESCRIPTION
        " "
::= { baseinfo1 33 }

outlet19WarnStatPDU11 OBJECT-TYPE
SYNTAX INTEGER (0..127)
ACCESS read-only
STATUS optional
DESCRIPTION
        " "
::= { baseinfo1 34 }

outlet20WarnStatPDU11 OBJECT-TYPE
SYNTAX INTEGER (0..127)
ACCESS read-only
STATUS optional
DESCRIPTION
        " "
::= { baseinfo1 35 }

outlet21WarnStatPDU11 OBJECT-TYPE
SYNTAX INTEGER (0..127)
ACCESS read-only
STATUS optional
DESCRIPTION
        " "
::= { baseinfo1 36 }

outlet22WarnStatPDU11 OBJECT-TYPE
SYNTAX INTEGER (0..127)
ACCESS read-only
STATUS optional
DESCRIPTION
        " "
::= { baseinfo1 37 }

outlet23WarnStatPDU11 OBJECT-TYPE
SYNTAX INTEGER (0..127)
ACCESS read-only
STATUS optional
DESCRIPTION
        " "
::= { baseinfo1 38 }

outlet24WarnStatPDU11 OBJECT-TYPE
SYNTAX INTEGER (0..127)
ACCESS read-only
STATUS optional
DESCRIPTION
        " "
::= { baseinfo1 39 }

outlet25WarnStatPDU11 OBJECT-TYPE
SYNTAX INTEGER (0..127)
ACCESS read-only
STATUS optional
DESCRIPTION
        " "
::= { baseinfo1 40 }

outlet26WarnStatPDU11 OBJECT-TYPE
SYNTAX INTEGER (0..127)
ACCESS read-only
STATUS optional
DESCRIPTION
        " "
::= { baseinfo1 41 }

outlet27WarnStatPDU11 OBJECT-TYPE
SYNTAX INTEGER (0..127)
ACCESS read-only
STATUS optional
DESCRIPTION
        " "
::= { baseinfo1 42 }

outlet28WarnStatPDU11 OBJECT-TYPE
SYNTAX INTEGER (0..127)
ACCESS read-only
STATUS optional
DESCRIPTION
        " "
::= { baseinfo1 43 }

outlet29WarnStatPDU11 OBJECT-TYPE
SYNTAX INTEGER (0..127)
ACCESS read-only
STATUS optional
DESCRIPTION
        " "
::= { baseinfo1 44 }

outlet30WarnStatPDU11 OBJECT-TYPE
SYNTAX INTEGER (0..127)
ACCESS read-only
STATUS optional
DESCRIPTION
        " "
::= { baseinfo1 45 }

outlet31WarnStatPDU11 OBJECT-TYPE
SYNTAX INTEGER (0..127)
ACCESS read-only
STATUS optional
DESCRIPTION
        " "
::= { baseinfo1 46 }

outlet32WarnStatPDU11 OBJECT-TYPE
SYNTAX INTEGER (0..127)
ACCESS read-only
STATUS optional
DESCRIPTION
        " "
::= { baseinfo1 47 }

outlet33WarnStatPDU11 OBJECT-TYPE
SYNTAX INTEGER (0..127)
ACCESS read-only
STATUS optional
DESCRIPTION
        " "
::= { baseinfo1 48 }

outlet34WarnStatPDU11 OBJECT-TYPE
SYNTAX INTEGER (0..127)
ACCESS read-only
STATUS optional
DESCRIPTION
        " "
::= { baseinfo1 49 }

outlet35WarnStatPDU11 OBJECT-TYPE
SYNTAX INTEGER (0..127)
ACCESS read-only
STATUS optional
DESCRIPTION
        " "
::= { baseinfo1 50 }

outlet36WarnStatPDU11 OBJECT-TYPE
SYNTAX INTEGER (0..127)
ACCESS read-only
STATUS optional
DESCRIPTION
        " "
::= { baseinfo1 51 }

input1 OBJECT IDENTIFIER ::= { pdu11 2 }

currentL1PDU11 OBJECT-TYPE
SYNTAX INTEGER (0..65535)
ACCESS read-only
STATUS optional
DESCRIPTION
        " "
::= { input1 1 }

voltageL1PDU11 OBJECT-TYPE
SYNTAX INTEGER (0..65535)
ACCESS read-only
STATUS optional
DESCRIPTION
        " "
::= { input1 2 }

powerL1PDU11 OBJECT-TYPE
SYNTAX INTEGER (0..65535)
ACCESS read-only
STATUS optional
DESCRIPTION
        " "
::= { input1 3 }

pfL1PDU11 OBJECT-TYPE
SYNTAX INTEGER (0..65535)
ACCESS read-only
STATUS optional
DESCRIPTION
        " "
::= { input1 4 }

energyL1PDU11 OBJECT-TYPE
SYNTAX INTEGER (0..65535)
ACCESS read-only
STATUS optional
DESCRIPTION
        " "
::= { input1 5 }

currentL2PDU11 OBJECT-TYPE
SYNTAX INTEGER (0..65535)
ACCESS read-only
STATUS optional
DESCRIPTION
        " "
::= { input1 6 }

voltageL2PDU11 OBJECT-TYPE
SYNTAX INTEGER (0..65535)
ACCESS read-only
STATUS optional
DESCRIPTION
        " "
::= { input1 7 }

powerL2PDU11 OBJECT-TYPE
SYNTAX INTEGER (0..65535)
ACCESS read-only
STATUS optional
DESCRIPTION
        " "
::= { input1 8 }

pfL2PDU11 OBJECT-TYPE
SYNTAX INTEGER (0..65535)
ACCESS read-only
STATUS optional
DESCRIPTION
        " "
::= { input1 9 }

energyL2PDU11 OBJECT-TYPE
SYNTAX INTEGER (0..65535)
ACCESS read-only
STATUS optional
DESCRIPTION
        " "
::= { input1 10 }

currentL3PDU11 OBJECT-TYPE
SYNTAX INTEGER (0..65535)
ACCESS read-only
STATUS optional
DESCRIPTION
        " "
::= { input1 11 }

voltageL3PDU11 OBJECT-TYPE
SYNTAX INTEGER (0..65535)
ACCESS read-only
STATUS optional
DESCRIPTION
        " "
::= { input1 12 }

powerL3PDU11 OBJECT-TYPE
SYNTAX INTEGER (0..65535)
ACCESS read-only
STATUS optional
DESCRIPTION
        " "
::= { input1 13 }

pfL3PDU11 OBJECT-TYPE
SYNTAX INTEGER (0..65535)
ACCESS read-only
STATUS optional
DESCRIPTION
        " "
::= { input1 14 }

energyL3PDU11 OBJECT-TYPE
SYNTAX INTEGER (0..65535)
ACCESS read-only
STATUS optional
DESCRIPTION
        " "
::= { input1 15 }

outletinfo1 OBJECT IDENTIFIER ::= { pdu11 3 }

outlet1PDU11 OBJECT IDENTIFIER ::= { outletinfo1 1 }

outlet2PDU11 OBJECT IDENTIFIER ::= { outletinfo1 2 }

outlet3PDU11 OBJECT IDENTIFIER ::= { outletinfo1 3 }

outlet4PDU11 OBJECT IDENTIFIER ::= { outletinfo1 4 }

outlet5PDU11 OBJECT IDENTIFIER ::= { outletinfo1 5 }

outlet6PDU11 OBJECT IDENTIFIER ::= { outletinfo1 6 }

outlet7PDU11 OBJECT IDENTIFIER ::= { outletinfo1 7 }

outlet8PDU11 OBJECT IDENTIFIER ::= { outletinfo1 8 }

outlet9PDU11 OBJECT IDENTIFIER ::= { outletinfo1 9 }

outlet10PDU11 OBJECT IDENTIFIER ::= { outletinfo1 10 }

outlet11PDU11 OBJECT IDENTIFIER ::= { outletinfo1 11 }

outlet12PDU11 OBJECT IDENTIFIER ::= { outletinfo1 12 }

outlet13PDU11 OBJECT IDENTIFIER ::= { outletinfo1 13 }

outlet14PDU11 OBJECT IDENTIFIER ::= { outletinfo1 14 }

outlet15PDU11 OBJECT IDENTIFIER ::= { outletinfo1 15 }

outlet16PDU11 OBJECT IDENTIFIER ::= { outletinfo1 16 }

outlet17PDU11 OBJECT IDENTIFIER ::= { outletinfo1 17 }

outlet18PDU11 OBJECT IDENTIFIER ::= { outletinfo1 18 }

outlet19PDU11 OBJECT IDENTIFIER ::= { outletinfo1 19 }

outlet20PDU11 OBJECT IDENTIFIER ::= { outletinfo1 20 }

outlet21PDU11 OBJECT IDENTIFIER ::= { outletinfo1 21 }

outlet22PDU11 OBJECT IDENTIFIER ::= { outletinfo1 22 }

outlet23PDU11 OBJECT IDENTIFIER ::= { outletinfo1 23 }

outlet24PDU11 OBJECT IDENTIFIER ::= { outletinfo1 24 }

outlet25PDU11 OBJECT IDENTIFIER ::= { outletinfo1 25 }

outlet26PDU11 OBJECT IDENTIFIER ::= { outletinfo1 26 }

outlet27PDU11 OBJECT IDENTIFIER ::= { outletinfo1 27 }

outlet28PDU11 OBJECT IDENTIFIER ::= { outletinfo1 28 }

outlet29PDU11 OBJECT IDENTIFIER ::= { outletinfo1 29 }

outlet30PDU11 OBJECT IDENTIFIER ::= { outletinfo1 30 }

outlet31PDU11 OBJECT IDENTIFIER ::= { outletinfo1 31 }

outlet32PDU11 OBJECT IDENTIFIER ::= { outletinfo1 32 }

outlet33PDU11 OBJECT IDENTIFIER ::= { outletinfo1 33 }

outlet34PDU11 OBJECT IDENTIFIER ::= { outletinfo1 34 }

outlet35PDU11 OBJECT IDENTIFIER ::= { outletinfo1 35 }

outlet36PDU11 OBJECT IDENTIFIER ::= { outletinfo1 36 }

switch1PDU11 OBJECT-TYPE
SYNTAX INTEGER (0..3)
ACCESS read-write
STATUS optional
DESCRIPTION
        " "
::= { outlet1PDU11 1 }

voltage1PDU11 OBJECT-TYPE
SYNTAX INTEGER (0..65535)
ACCESS read-only
STATUS optional
DESCRIPTION
        " "
::= { outlet1PDU11 2 }

current1PDU11 OBJECT-TYPE
SYNTAX INTEGER (0..65535)
ACCESS read-only
STATUS optional
DESCRIPTION
        " "
::= { outlet1PDU11 3 }

power1PDU11 OBJECT-TYPE
SYNTAX INTEGER (0..65535)
ACCESS read-only
STATUS optional
DESCRIPTION
        " "
::= { outlet1PDU11 4 }

pf1PDU11 OBJECT-TYPE
SYNTAX INTEGER (0..65535)
ACCESS read-only
STATUS optional
DESCRIPTION
        " "
::= { outlet1PDU11 5 }

energy1PDU11 OBJECT-TYPE
SYNTAX INTEGER (0..65535)
ACCESS read-only
STATUS optional
DESCRIPTION
        " "
::= { outlet1PDU11 6 }

switch2PDU11 OBJECT-TYPE
SYNTAX INTEGER (0..3)
ACCESS read-write
STATUS optional
DESCRIPTION
        " "
::= { outlet2PDU11 1 }

voltage2PDU11 OBJECT-TYPE
SYNTAX INTEGER (0..65535)
ACCESS read-only
STATUS optional
DESCRIPTION
        " "
::= { outlet2PDU11 2 }

current2PDU11 OBJECT-TYPE
SYNTAX INTEGER (0..65535)
ACCESS read-only
STATUS optional
DESCRIPTION
        " "
::= { outlet2PDU11 3 }

power2PDU11 OBJECT-TYPE
SYNTAX INTEGER (0..65535)
ACCESS read-only
STATUS optional
DESCRIPTION
        " "
::= { outlet2PDU11 4 }

pf2PDU11 OBJECT-TYPE
SYNTAX INTEGER (0..65535)
ACCESS read-only
STATUS optional
DESCRIPTION
        " "
::= { outlet2PDU11 5 }

energy2PDU11 OBJECT-TYPE
SYNTAX INTEGER (0..65535)
ACCESS read-only
STATUS optional
DESCRIPTION
        " "
::= { outlet2PDU11 6 }

switch3PDU11 OBJECT-TYPE
SYNTAX INTEGER (0..3)
ACCESS read-write
STATUS optional
DESCRIPTION
        " "
::= { outlet3PDU11 1 }

voltage3PDU11 OBJECT-TYPE
SYNTAX INTEGER (0..65535)
ACCESS read-only
STATUS optional
DESCRIPTION
        " "
::= { outlet3PDU11 2 }

current3PDU11 OBJECT-TYPE
SYNTAX INTEGER (0..65535)
ACCESS read-only
STATUS optional
DESCRIPTION
        " "
::= { outlet3PDU11 3 }

power3PDU11 OBJECT-TYPE
SYNTAX INTEGER (0..65535)
ACCESS read-only
STATUS optional
DESCRIPTION
        " "
::= { outlet3PDU11 4 }

pf3PDU11 OBJECT-TYPE
SYNTAX INTEGER (0..65535)
ACCESS read-only
STATUS optional
DESCRIPTION
        " "
::= { outlet3PDU11 5 }

energy3PDU11 OBJECT-TYPE
SYNTAX INTEGER (0..65535)
ACCESS read-only
STATUS optional
DESCRIPTION
        " "
::= { outlet3PDU11 6 }

switch4PDU11 OBJECT-TYPE
SYNTAX INTEGER (0..3)
ACCESS read-write
STATUS optional
DESCRIPTION
        " "
::= { outlet4PDU11 1 }

voltage4PDU11 OBJECT-TYPE
SYNTAX INTEGER (0..65535)
ACCESS read-only
STATUS optional
DESCRIPTION
        " "
::= { outlet4PDU11 2 }

current4PDU11 OBJECT-TYPE
SYNTAX INTEGER (0..65535)
ACCESS read-only
STATUS optional
DESCRIPTION
        " "
::= { outlet4PDU11 3 }

power4PDU11 OBJECT-TYPE
SYNTAX INTEGER (0..65535)
ACCESS read-only
STATUS optional
DESCRIPTION
        " "
::= { outlet4PDU11 4 }

pf4PDU11 OBJECT-TYPE
SYNTAX INTEGER (0..65535)
ACCESS read-only
STATUS optional
DESCRIPTION
        " "
::= { outlet4PDU11 5 }

energy4PDU11 OBJECT-TYPE
SYNTAX INTEGER (0..65535)
ACCESS read-only
STATUS optional
DESCRIPTION
        " "
::= { outlet4PDU11 6 }

switch5PDU11 OBJECT-TYPE
SYNTAX INTEGER (0..3)
ACCESS read-write
STATUS optional
DESCRIPTION
        " "
::= { outlet5PDU11 1 }

voltage5PDU11 OBJECT-TYPE
SYNTAX INTEGER (0..65535)
ACCESS read-only
STATUS optional
DESCRIPTION
        " "
::= { outlet5PDU11 2 }

current5PDU11 OBJECT-TYPE
SYNTAX INTEGER (0..65535)
ACCESS read-only
STATUS optional
DESCRIPTION
        " "
::= { outlet5PDU11 3 }

power5PDU11 OBJECT-TYPE
SYNTAX INTEGER (0..65535)
ACCESS read-only
STATUS optional
DESCRIPTION
        " "
::= { outlet5PDU11 4 }

pf5PDU11 OBJECT-TYPE
SYNTAX INTEGER (0..65535)
ACCESS read-only
STATUS optional
DESCRIPTION
        " "
::= { outlet5PDU11 5 }

energy5PDU11 OBJECT-TYPE
SYNTAX INTEGER (0..65535)
ACCESS read-only
STATUS optional
DESCRIPTION
        " "
::= { outlet5PDU11 6 }

switch6PDU11 OBJECT-TYPE
SYNTAX INTEGER (0..3)
ACCESS read-write
STATUS optional
DESCRIPTION
        " "
::= { outlet6PDU11 1 }

voltage6PDU11 OBJECT-TYPE
SYNTAX INTEGER (0..65535)
ACCESS read-only
STATUS optional
DESCRIPTION
        " "
::= { outlet6PDU11 2 }

current6PDU11 OBJECT-TYPE
SYNTAX INTEGER (0..65535)
ACCESS read-only
STATUS optional
DESCRIPTION
        " "
::= { outlet6PDU11 3 }

power6PDU11 OBJECT-TYPE
SYNTAX INTEGER (0..65535)
ACCESS read-only
STATUS optional
DESCRIPTION
        " "
::= { outlet6PDU11 4 }

pf6PDU11 OBJECT-TYPE
SYNTAX INTEGER (0..65535)
ACCESS read-only
STATUS optional
DESCRIPTION
        " "
::= { outlet6PDU11 5 }

energy6PDU11 OBJECT-TYPE
SYNTAX INTEGER (0..65535)
ACCESS read-only
STATUS optional
DESCRIPTION
        " "
::= { outlet6PDU11 6 }

switch7PDU11 OBJECT-TYPE
SYNTAX INTEGER (0..3)
ACCESS read-write
STATUS optional
DESCRIPTION
        " "
::= { outlet7PDU11 1 }

voltage7PDU11 OBJECT-TYPE
SYNTAX INTEGER (0..65535)
ACCESS read-only
STATUS optional
DESCRIPTION
        " "
::= { outlet7PDU11 2 }

current7PDU11 OBJECT-TYPE
SYNTAX INTEGER (0..65535)
ACCESS read-only
STATUS optional
DESCRIPTION
        " "
::= { outlet7PDU11 3 }

power7PDU11 OBJECT-TYPE
SYNTAX INTEGER (0..65535)
ACCESS read-only
STATUS optional
DESCRIPTION
        " "
::= { outlet7PDU11 4 }

pf7PDU11 OBJECT-TYPE
SYNTAX INTEGER (0..65535)
ACCESS read-only
STATUS optional
DESCRIPTION
        " "
::= { outlet7PDU11 5 }

energy7PDU11 OBJECT-TYPE
SYNTAX INTEGER (0..65535)
ACCESS read-only
STATUS optional
DESCRIPTION
        " "
::= { outlet7PDU11 6 }

switch8PDU11 OBJECT-TYPE
SYNTAX INTEGER (0..3)
ACCESS read-write
STATUS optional
DESCRIPTION
        " "
::= { outlet8PDU11 1 }

voltage8PDU11 OBJECT-TYPE
SYNTAX INTEGER (0..65535)
ACCESS read-only
STATUS optional
DESCRIPTION
        " "
::= { outlet8PDU11 2 }

current8PDU11 OBJECT-TYPE
SYNTAX INTEGER (0..65535)
ACCESS read-only
STATUS optional
DESCRIPTION
        " "
::= { outlet8PDU11 3 }

power8PDU11 OBJECT-TYPE
SYNTAX INTEGER (0..65535)
ACCESS read-only
STATUS optional
DESCRIPTION
        " "
::= { outlet8PDU11 4 }

pf8PDU11 OBJECT-TYPE
SYNTAX INTEGER (0..65535)
ACCESS read-only
STATUS optional
DESCRIPTION
        " "
::= { outlet8PDU11 5 }

energy8PDU11 OBJECT-TYPE
SYNTAX INTEGER (0..65535)
ACCESS read-only
STATUS optional
DESCRIPTION
        " "
::= { outlet8PDU11 6 }

switch9PDU11 OBJECT-TYPE
SYNTAX INTEGER (0..3)
ACCESS read-write
STATUS optional
DESCRIPTION
        " "
::= { outlet9PDU11 1 }

voltage9PDU11 OBJECT-TYPE
SYNTAX INTEGER (0..65535)
ACCESS read-only
STATUS optional
DESCRIPTION
        " "
::= { outlet9PDU11 2 }

current9PDU11 OBJECT-TYPE
SYNTAX INTEGER (0..65535)
ACCESS read-only
STATUS optional
DESCRIPTION
        " "
::= { outlet9PDU11 3 }

power9PDU11 OBJECT-TYPE
SYNTAX INTEGER (0..65535)
ACCESS read-only
STATUS optional
DESCRIPTION
        " "
::= { outlet9PDU11 4 }

pf9PDU11 OBJECT-TYPE
SYNTAX INTEGER (0..65535)
ACCESS read-only
STATUS optional
DESCRIPTION
        " "
::= { outlet9PDU11 5 }

energy9PDU11 OBJECT-TYPE
SYNTAX INTEGER (0..65535)
ACCESS read-only
STATUS optional
DESCRIPTION
        " "
::= { outlet9PDU11 6 }

switch10PDU11 OBJECT-TYPE
SYNTAX INTEGER (0..3)
ACCESS read-write
STATUS optional
DESCRIPTION
        " "
::= { outlet10PDU11 1 }

voltage10PDU11 OBJECT-TYPE
SYNTAX INTEGER (0..65535)
ACCESS read-only
STATUS optional
DESCRIPTION
        " "
::= { outlet10PDU11 2 }

current10PDU11 OBJECT-TYPE
SYNTAX INTEGER (0..65535)
ACCESS read-only
STATUS optional
DESCRIPTION
        " "
::= { outlet10PDU11 3 }

power10PDU11 OBJECT-TYPE
SYNTAX INTEGER (0..65535)
ACCESS read-only
STATUS optional
DESCRIPTION
        " "
::= { outlet10PDU11 4 }

pf10PDU11 OBJECT-TYPE
SYNTAX INTEGER (0..65535)
ACCESS read-only
STATUS optional
DESCRIPTION
        " "
::= { outlet10PDU11 5 }

energy10PDU11 OBJECT-TYPE
SYNTAX INTEGER (0..65535)
ACCESS read-only
STATUS optional
DESCRIPTION
        " "
::= { outlet10PDU11 6 }

switch11PDU11 OBJECT-TYPE
SYNTAX INTEGER (0..3)
ACCESS read-write
STATUS optional
DESCRIPTION
        " "
::= { outlet11PDU11 1 }

voltage11PDU11 OBJECT-TYPE
SYNTAX INTEGER (0..65535)
ACCESS read-only
STATUS optional
DESCRIPTION
        " "
::= { outlet11PDU11 2 }

current11PDU11 OBJECT-TYPE
SYNTAX INTEGER (0..65535)
ACCESS read-only
STATUS optional
DESCRIPTION
        " "
::= { outlet11PDU11 3 }

power11PDU11 OBJECT-TYPE
SYNTAX INTEGER (0..65535)
ACCESS read-only
STATUS optional
DESCRIPTION
        " "
::= { outlet11PDU11 4 }

pf11PDU11 OBJECT-TYPE
SYNTAX INTEGER (0..65535)
ACCESS read-only
STATUS optional
DESCRIPTION
        " "
::= { outlet11PDU11 5 }

energy11PDU11 OBJECT-TYPE
SYNTAX INTEGER (0..65535)
ACCESS read-only
STATUS optional
DESCRIPTION
        " "
::= { outlet11PDU11 6 }

switch12PDU11 OBJECT-TYPE
SYNTAX INTEGER (0..3)
ACCESS read-write
STATUS optional
DESCRIPTION
        " "
::= { outlet12PDU11 1 }

voltage12PDU11 OBJECT-TYPE
SYNTAX INTEGER (0..65535)
ACCESS read-only
STATUS optional
DESCRIPTION
        " "
::= { outlet12PDU11 2 }

current12PDU11 OBJECT-TYPE
SYNTAX INTEGER (0..65535)
ACCESS read-only
STATUS optional
DESCRIPTION
        " "
::= { outlet12PDU11 3 }

power12PDU11 OBJECT-TYPE
SYNTAX INTEGER (0..65535)
ACCESS read-only
STATUS optional
DESCRIPTION
        " "
::= { outlet12PDU11 4 }

pf12PDU11 OBJECT-TYPE
SYNTAX INTEGER (0..65535)
ACCESS read-only
STATUS optional
DESCRIPTION
        " "
::= { outlet12PDU11 5 }

energy12PDU11 OBJECT-TYPE
SYNTAX INTEGER (0..65535)
ACCESS read-only
STATUS optional
DESCRIPTION
        " "
::= { outlet12PDU11 6 }

switch13PDU11 OBJECT-TYPE
SYNTAX INTEGER (0..3)
ACCESS read-write
STATUS optional
DESCRIPTION
        " "
::= { outlet13PDU11 1 }

voltage13PDU11 OBJECT-TYPE
SYNTAX INTEGER (0..65535)
ACCESS read-only
STATUS optional
DESCRIPTION
        " "
::= { outlet13PDU11 2 }

current13PDU11 OBJECT-TYPE
SYNTAX INTEGER (0..65535)
ACCESS read-only
STATUS optional
DESCRIPTION
        " "
::= { outlet13PDU11 3 }

power13PDU11 OBJECT-TYPE
SYNTAX INTEGER (0..65535)
ACCESS read-only
STATUS optional
DESCRIPTION
        " "
::= { outlet13PDU11 4 }

pf13PDU11 OBJECT-TYPE
SYNTAX INTEGER (0..65535)
ACCESS read-only
STATUS optional
DESCRIPTION
        " "
::= { outlet13PDU11 5 }

energy13PDU11 OBJECT-TYPE
SYNTAX INTEGER (0..65535)
ACCESS read-only
STATUS optional
DESCRIPTION
        " "
::= { outlet13PDU11 6 }

switch14PDU11 OBJECT-TYPE
SYNTAX INTEGER (0..3)
ACCESS read-write
STATUS optional
DESCRIPTION
        " "
::= { outlet14PDU11 1 }

voltage14PDU11 OBJECT-TYPE
SYNTAX INTEGER (0..65535)
ACCESS read-only
STATUS optional
DESCRIPTION
        " "
::= { outlet14PDU11 2 }

current14PDU11 OBJECT-TYPE
SYNTAX INTEGER (0..65535)
ACCESS read-only
STATUS optional
DESCRIPTION
        " "
::= { outlet14PDU11 3 }

power14PDU11 OBJECT-TYPE
SYNTAX INTEGER (0..65535)
ACCESS read-only
STATUS optional
DESCRIPTION
        " "
::= { outlet14PDU11 4 }

pf14PDU11 OBJECT-TYPE
SYNTAX INTEGER (0..65535)
ACCESS read-only
STATUS optional
DESCRIPTION
        " "
::= { outlet14PDU11 5 }

energy14PDU11 OBJECT-TYPE
SYNTAX INTEGER (0..65535)
ACCESS read-only
STATUS optional
DESCRIPTION
        " "
::= { outlet14PDU11 6 }

switch15PDU11 OBJECT-TYPE
SYNTAX INTEGER (0..3)
ACCESS read-write
STATUS optional
DESCRIPTION
        " "
::= { outlet15PDU11 1 }

voltage15PDU11 OBJECT-TYPE
SYNTAX INTEGER (0..65535)
ACCESS read-only
STATUS optional
DESCRIPTION
        " "
::= { outlet15PDU11 2 }

current15PDU11 OBJECT-TYPE
SYNTAX INTEGER (0..65535)
ACCESS read-only
STATUS optional
DESCRIPTION
        " "
::= { outlet15PDU11 3 }

power15PDU11 OBJECT-TYPE
SYNTAX INTEGER (0..65535)
ACCESS read-only
STATUS optional
DESCRIPTION
        " "
::= { outlet15PDU11 4 }

pf15PDU11 OBJECT-TYPE
SYNTAX INTEGER (0..65535)
ACCESS read-only
STATUS optional
DESCRIPTION
        " "
::= { outlet15PDU11 5 }

energy15PDU11 OBJECT-TYPE
SYNTAX INTEGER (0..65535)
ACCESS read-only
STATUS optional
DESCRIPTION
        " "
::= { outlet15PDU11 6 }

switch16PDU11 OBJECT-TYPE
SYNTAX INTEGER (0..3)
ACCESS read-write
STATUS optional
DESCRIPTION
        " "
::= { outlet16PDU11 1 }

voltage16PDU11 OBJECT-TYPE
SYNTAX INTEGER (0..65535)
ACCESS read-only
STATUS optional
DESCRIPTION
        " "
::= { outlet16PDU11 2 }

current16PDU11 OBJECT-TYPE
SYNTAX INTEGER (0..65535)
ACCESS read-only
STATUS optional
DESCRIPTION
        " "
::= { outlet16PDU11 3 }

power16PDU11 OBJECT-TYPE
SYNTAX INTEGER (0..65535)
ACCESS read-only
STATUS optional
DESCRIPTION
        " "
::= { outlet16PDU11 4 }

pf16PDU11 OBJECT-TYPE
SYNTAX INTEGER (0..65535)
ACCESS read-only
STATUS optional
DESCRIPTION
        " "
::= { outlet16PDU11 5 }

energy16PDU11 OBJECT-TYPE
SYNTAX INTEGER (0..65535)
ACCESS read-only
STATUS optional
DESCRIPTION
        " "
::= { outlet16PDU11 6 }

switch17PDU11 OBJECT-TYPE
SYNTAX INTEGER (0..3)
ACCESS read-write
STATUS optional
DESCRIPTION
        " "
::= { outlet17PDU11 1 }

voltage17PDU11 OBJECT-TYPE
SYNTAX INTEGER (0..65535)
ACCESS read-only
STATUS optional
DESCRIPTION
        " "
::= { outlet17PDU11 2 }

current17PDU11 OBJECT-TYPE
SYNTAX INTEGER (0..65535)
ACCESS read-only
STATUS optional
DESCRIPTION
        " "
::= { outlet17PDU11 3 }

power17PDU11 OBJECT-TYPE
SYNTAX INTEGER (0..65535)
ACCESS read-only
STATUS optional
DESCRIPTION
        " "
::= { outlet17PDU11 4 }

pf17PDU11 OBJECT-TYPE
SYNTAX INTEGER (0..65535)
ACCESS read-only
STATUS optional
DESCRIPTION
        " "
::= { outlet17PDU11 5 }

energy17PDU11 OBJECT-TYPE
SYNTAX INTEGER (0..65535)
ACCESS read-only
STATUS optional
DESCRIPTION
        " "
::= { outlet17PDU11 6 }

switch18PDU11 OBJECT-TYPE
SYNTAX INTEGER (0..3)
ACCESS read-write
STATUS optional
DESCRIPTION
        " "
::= { outlet18PDU11 1 }

voltage18PDU11 OBJECT-TYPE
SYNTAX INTEGER (0..65535)
ACCESS read-only
STATUS optional
DESCRIPTION
        " "
::= { outlet18PDU11 2 }

current18PDU11 OBJECT-TYPE
SYNTAX INTEGER (0..65535)
ACCESS read-only
STATUS optional
DESCRIPTION
        " "
::= { outlet18PDU11 3 }

power18PDU11 OBJECT-TYPE
SYNTAX INTEGER (0..65535)
ACCESS read-only
STATUS optional
DESCRIPTION
        " "
::= { outlet18PDU11 4 }

pf18PDU11 OBJECT-TYPE
SYNTAX INTEGER (0..65535)
ACCESS read-only
STATUS optional
DESCRIPTION
        " "
::= { outlet18PDU11 5 }

energy18PDU11 OBJECT-TYPE
SYNTAX INTEGER (0..65535)
ACCESS read-only
STATUS optional
DESCRIPTION
        " "
::= { outlet18PDU11 6 }

switch19PDU11 OBJECT-TYPE
SYNTAX INTEGER (0..3)
ACCESS read-write
STATUS optional
DESCRIPTION
        " "
::= { outlet19PDU11 1 }

voltage19PDU11 OBJECT-TYPE
SYNTAX INTEGER (0..65535)
ACCESS read-only
STATUS optional
DESCRIPTION
        " "
::= { outlet19PDU11 2 }

current19PDU11 OBJECT-TYPE
SYNTAX INTEGER (0..65535)
ACCESS read-only
STATUS optional
DESCRIPTION
        " "
::= { outlet19PDU11 3 }

power19PDU11 OBJECT-TYPE
SYNTAX INTEGER (0..65535)
ACCESS read-only
STATUS optional
DESCRIPTION
        " "
::= { outlet19PDU11 4 }

pf19PDU11 OBJECT-TYPE
SYNTAX INTEGER (0..65535)
ACCESS read-only
STATUS optional
DESCRIPTION
        " "
::= { outlet19PDU11 5 }

energy19PDU11 OBJECT-TYPE
SYNTAX INTEGER (0..65535)
ACCESS read-only
STATUS optional
DESCRIPTION
        " "
::= { outlet19PDU11 6 }

switch20PDU11 OBJECT-TYPE
SYNTAX INTEGER (0..3)
ACCESS read-write
STATUS optional
DESCRIPTION
        " "
::= { outlet20PDU11 1 }

voltage20PDU11 OBJECT-TYPE
SYNTAX INTEGER (0..65535)
ACCESS read-only
STATUS optional
DESCRIPTION
        " "
::= { outlet20PDU11 2 }

current20PDU11 OBJECT-TYPE
SYNTAX INTEGER (0..65535)
ACCESS read-only
STATUS optional
DESCRIPTION
        " "
::= { outlet20PDU11 3 }

power20PDU11 OBJECT-TYPE
SYNTAX INTEGER (0..65535)
ACCESS read-only
STATUS optional
DESCRIPTION
        " "
::= { outlet20PDU11 4 }

pf20PDU11 OBJECT-TYPE
SYNTAX INTEGER (0..65535)
ACCESS read-only
STATUS optional
DESCRIPTION
        " "
::= { outlet20PDU11 5 }

energy20PDU11 OBJECT-TYPE
SYNTAX INTEGER (0..65535)
ACCESS read-only
STATUS optional
DESCRIPTION
        " "
::= { outlet20PDU11 6 }

switch21PDU11 OBJECT-TYPE
SYNTAX INTEGER (0..3)
ACCESS read-write
STATUS optional
DESCRIPTION
        " "
::= { outlet21PDU11 1 }

voltage21PDU11 OBJECT-TYPE
SYNTAX INTEGER (0..65535)
ACCESS read-only
STATUS optional
DESCRIPTION
        " "
::= { outlet21PDU11 2 }

current21PDU11 OBJECT-TYPE
SYNTAX INTEGER (0..65535)
ACCESS read-only
STATUS optional
DESCRIPTION
        " "
::= { outlet21PDU11 3 }

power21PDU11 OBJECT-TYPE
SYNTAX INTEGER (0..65535)
ACCESS read-only
STATUS optional
DESCRIPTION
        " "
::= { outlet21PDU11 4 }

pf21PDU11 OBJECT-TYPE
SYNTAX INTEGER (0..65535)
ACCESS read-only
STATUS optional
DESCRIPTION
        " "
::= { outlet21PDU11 5 }

energy21PDU11 OBJECT-TYPE
SYNTAX INTEGER (0..65535)
ACCESS read-only
STATUS optional
DESCRIPTION
        " "
::= { outlet21PDU11 6 }

switch22PDU11 OBJECT-TYPE
SYNTAX INTEGER (0..3)
ACCESS read-write
STATUS optional
DESCRIPTION
        " "
::= { outlet22PDU11 1 }

voltage22PDU11 OBJECT-TYPE
SYNTAX INTEGER (0..65535)
ACCESS read-only
STATUS optional
DESCRIPTION
        " "
::= { outlet22PDU11 2 }

current22PDU11 OBJECT-TYPE
SYNTAX INTEGER (0..65535)
ACCESS read-only
STATUS optional
DESCRIPTION
        " "
::= { outlet22PDU11 3 }

power22PDU11 OBJECT-TYPE
SYNTAX INTEGER (0..65535)
ACCESS read-only
STATUS optional
DESCRIPTION
        " "
::= { outlet22PDU11 4 }

pf22PDU11 OBJECT-TYPE
SYNTAX INTEGER (0..65535)
ACCESS read-only
STATUS optional
DESCRIPTION
        " "
::= { outlet22PDU11 5 }

energy22PDU11 OBJECT-TYPE
SYNTAX INTEGER (0..65535)
ACCESS read-only
STATUS optional
DESCRIPTION
        " "
::= { outlet22PDU11 6 }

switch23PDU11 OBJECT-TYPE
SYNTAX INTEGER (0..3)
ACCESS read-write
STATUS optional
DESCRIPTION
        " "
::= { outlet23PDU11 1 }

voltage23PDU11 OBJECT-TYPE
SYNTAX INTEGER (0..65535)
ACCESS read-only
STATUS optional
DESCRIPTION
        " "
::= { outlet23PDU11 2 }

current23PDU11 OBJECT-TYPE
SYNTAX INTEGER (0..65535)
ACCESS read-only
STATUS optional
DESCRIPTION
        " "
::= { outlet23PDU11 3 }

power23PDU11 OBJECT-TYPE
SYNTAX INTEGER (0..65535)
ACCESS read-only
STATUS optional
DESCRIPTION
        " "
::= { outlet23PDU11 4 }

pf23PDU11 OBJECT-TYPE
SYNTAX INTEGER (0..65535)
ACCESS read-only
STATUS optional
DESCRIPTION
        " "
::= { outlet23PDU11 5 }

energy23PDU11 OBJECT-TYPE
SYNTAX INTEGER (0..65535)
ACCESS read-only
STATUS optional
DESCRIPTION
        " "
::= { outlet23PDU11 6 }

switch24PDU11 OBJECT-TYPE
SYNTAX INTEGER (0..3)
ACCESS read-write
STATUS optional
DESCRIPTION
        " "
::= { outlet24PDU11 1 }

voltage24PDU11 OBJECT-TYPE
SYNTAX INTEGER (0..65535)
ACCESS read-only
STATUS optional
DESCRIPTION
        " "
::= { outlet24PDU11 2 }

current24PDU11 OBJECT-TYPE
SYNTAX INTEGER (0..65535)
ACCESS read-only
STATUS optional
DESCRIPTION
        " "
::= { outlet24PDU11 3 }

power24PDU11 OBJECT-TYPE
SYNTAX INTEGER (0..65535)
ACCESS read-only
STATUS optional
DESCRIPTION
        " "
::= { outlet24PDU11 4 }

pf24PDU11 OBJECT-TYPE
SYNTAX INTEGER (0..65535)
ACCESS read-only
STATUS optional
DESCRIPTION
        " "
::= { outlet24PDU11 5 }

energy24PDU11 OBJECT-TYPE
SYNTAX INTEGER (0..65535)
ACCESS read-only
STATUS optional
DESCRIPTION
        " "
::= { outlet24PDU11 6 }

switch25PDU11 OBJECT-TYPE
SYNTAX INTEGER (0..3)
ACCESS read-write
STATUS optional
DESCRIPTION
        " "
::= { outlet25PDU11 1 }

voltage25PDU11 OBJECT-TYPE
SYNTAX INTEGER (0..65535)
ACCESS read-only
STATUS optional
DESCRIPTION
        " "
::= { outlet25PDU11 2 }

current25PDU11 OBJECT-TYPE
SYNTAX INTEGER (0..65535)
ACCESS read-only
STATUS optional
DESCRIPTION
        " "
::= { outlet25PDU11 3 }

power25PDU11 OBJECT-TYPE
SYNTAX INTEGER (0..65535)
ACCESS read-only
STATUS optional
DESCRIPTION
        " "
::= { outlet25PDU11 4 }

pf25PDU11 OBJECT-TYPE
SYNTAX INTEGER (0..65535)
ACCESS read-only
STATUS optional
DESCRIPTION
        " "
::= { outlet25PDU11 5 }

energy25PDU11 OBJECT-TYPE
SYNTAX INTEGER (0..65535)
ACCESS read-only
STATUS optional
DESCRIPTION
        " "
::= { outlet25PDU11 6 }

switch26PDU11 OBJECT-TYPE
SYNTAX INTEGER (0..3)
ACCESS read-write
STATUS optional
DESCRIPTION
        " "
::= { outlet26PDU11 1 }

voltage26PDU11 OBJECT-TYPE
SYNTAX INTEGER (0..65535)
ACCESS read-only
STATUS optional
DESCRIPTION
        " "
::= { outlet26PDU11 2 }

current26PDU11 OBJECT-TYPE
SYNTAX INTEGER (0..65535)
ACCESS read-only
STATUS optional
DESCRIPTION
        " "
::= { outlet26PDU11 3 }

power26PDU11 OBJECT-TYPE
SYNTAX INTEGER (0..65535)
ACCESS read-only
STATUS optional
DESCRIPTION
        " "
::= { outlet26PDU11 4 }

pf26PDU11 OBJECT-TYPE
SYNTAX INTEGER (0..65535)
ACCESS read-only
STATUS optional
DESCRIPTION
        " "
::= { outlet26PDU11 5 }

energy26PDU11 OBJECT-TYPE
SYNTAX INTEGER (0..65535)
ACCESS read-only
STATUS optional
DESCRIPTION
        " "
::= { outlet26PDU11 6 }

switch27PDU11 OBJECT-TYPE
SYNTAX INTEGER (0..3)
ACCESS read-write
STATUS optional
DESCRIPTION
        " "
::= { outlet27PDU11 1 }

voltage27PDU11 OBJECT-TYPE
SYNTAX INTEGER (0..65535)
ACCESS read-only
STATUS optional
DESCRIPTION
        " "
::= { outlet27PDU11 2 }

current27PDU11 OBJECT-TYPE
SYNTAX INTEGER (0..65535)
ACCESS read-only
STATUS optional
DESCRIPTION
        " "
::= { outlet27PDU11 3 }

power27PDU11 OBJECT-TYPE
SYNTAX INTEGER (0..65535)
ACCESS read-only
STATUS optional
DESCRIPTION
        " "
::= { outlet27PDU11 4 }

pf27PDU11 OBJECT-TYPE
SYNTAX INTEGER (0..65535)
ACCESS read-only
STATUS optional
DESCRIPTION
        " "
::= { outlet27PDU11 5 }

energy27PDU11 OBJECT-TYPE
SYNTAX INTEGER (0..65535)
ACCESS read-only
STATUS optional
DESCRIPTION
        " "
::= { outlet27PDU11 6 }

switch28PDU11 OBJECT-TYPE
SYNTAX INTEGER (0..3)
ACCESS read-write
STATUS optional
DESCRIPTION
        " "
::= { outlet28PDU11 1 }

voltage28PDU11 OBJECT-TYPE
SYNTAX INTEGER (0..65535)
ACCESS read-only
STATUS optional
DESCRIPTION
        " "
::= { outlet28PDU11 2 }

current28PDU11 OBJECT-TYPE
SYNTAX INTEGER (0..65535)
ACCESS read-only
STATUS optional
DESCRIPTION
        " "
::= { outlet28PDU11 3 }

power28PDU11 OBJECT-TYPE
SYNTAX INTEGER (0..65535)
ACCESS read-only
STATUS optional
DESCRIPTION
        " "
::= { outlet28PDU11 4 }

pf28PDU11 OBJECT-TYPE
SYNTAX INTEGER (0..65535)
ACCESS read-only
STATUS optional
DESCRIPTION
        " "
::= { outlet28PDU11 5 }

energy28PDU11 OBJECT-TYPE
SYNTAX INTEGER (0..65535)
ACCESS read-only
STATUS optional
DESCRIPTION
        " "
::= { outlet28PDU11 6 }

switch29PDU11 OBJECT-TYPE
SYNTAX INTEGER (0..3)
ACCESS read-write
STATUS optional
DESCRIPTION
        " "
::= { outlet29PDU11 1 }

voltage29PDU11 OBJECT-TYPE
SYNTAX INTEGER (0..65535)
ACCESS read-only
STATUS optional
DESCRIPTION
        " "
::= { outlet29PDU11 2 }

current29PDU11 OBJECT-TYPE
SYNTAX INTEGER (0..65535)
ACCESS read-only
STATUS optional
DESCRIPTION
        " "
::= { outlet29PDU11 3 }

power29PDU11 OBJECT-TYPE
SYNTAX INTEGER (0..65535)
ACCESS read-only
STATUS optional
DESCRIPTION
        " "
::= { outlet29PDU11 4 }

pf29PDU11 OBJECT-TYPE
SYNTAX INTEGER (0..65535)
ACCESS read-only
STATUS optional
DESCRIPTION
        " "
::= { outlet29PDU11 5 }

energy29PDU11 OBJECT-TYPE
SYNTAX INTEGER (0..65535)
ACCESS read-only
STATUS optional
DESCRIPTION
        " "
::= { outlet29PDU11 6 }

switch30PDU11 OBJECT-TYPE
SYNTAX INTEGER (0..3)
ACCESS read-write
STATUS optional
DESCRIPTION
        " "
::= { outlet30PDU11 1 }

voltage30PDU11 OBJECT-TYPE
SYNTAX INTEGER (0..65535)
ACCESS read-only
STATUS optional
DESCRIPTION
        " "
::= { outlet30PDU11 2 }

current30PDU11 OBJECT-TYPE
SYNTAX INTEGER (0..65535)
ACCESS read-only
STATUS optional
DESCRIPTION
        " "
::= { outlet30PDU11 3 }

power30PDU11 OBJECT-TYPE
SYNTAX INTEGER (0..65535)
ACCESS read-only
STATUS optional
DESCRIPTION
        " "
::= { outlet30PDU11 4 }

pf30PDU11 OBJECT-TYPE
SYNTAX INTEGER (0..65535)
ACCESS read-only
STATUS optional
DESCRIPTION
        " "
::= { outlet30PDU11 5 }

energy30PDU11 OBJECT-TYPE
SYNTAX INTEGER (0..65535)
ACCESS read-only
STATUS optional
DESCRIPTION
        " "
::= { outlet30PDU11 6 }

switch31PDU11 OBJECT-TYPE
SYNTAX INTEGER (0..3)
ACCESS read-write
STATUS optional
DESCRIPTION
        " "
::= { outlet31PDU11 1 }

voltage31PDU11 OBJECT-TYPE
SYNTAX INTEGER (0..65535)
ACCESS read-only
STATUS optional
DESCRIPTION
        " "
::= { outlet31PDU11 2 }

current31PDU11 OBJECT-TYPE
SYNTAX INTEGER (0..65535)
ACCESS read-only
STATUS optional
DESCRIPTION
        " "
::= { outlet31PDU11 3 }

power31PDU11 OBJECT-TYPE
SYNTAX INTEGER (0..65535)
ACCESS read-only
STATUS optional
DESCRIPTION
        " "
::= { outlet31PDU11 4 }

pf31PDU11 OBJECT-TYPE
SYNTAX INTEGER (0..65535)
ACCESS read-only
STATUS optional
DESCRIPTION
        " "
::= { outlet31PDU11 5 }

energy31PDU11 OBJECT-TYPE
SYNTAX INTEGER (0..65535)
ACCESS read-only
STATUS optional
DESCRIPTION
        " "
::= { outlet31PDU11 6 }

switch32PDU11 OBJECT-TYPE
SYNTAX INTEGER (0..3)
ACCESS read-write
STATUS optional
DESCRIPTION
        " "
::= { outlet32PDU11 1 }

voltage32PDU11 OBJECT-TYPE
SYNTAX INTEGER (0..65535)
ACCESS read-only
STATUS optional
DESCRIPTION
        " "
::= { outlet32PDU11 2 }

current32PDU11 OBJECT-TYPE
SYNTAX INTEGER (0..65535)
ACCESS read-only
STATUS optional
DESCRIPTION
        " "
::= { outlet32PDU11 3 }

power32PDU11 OBJECT-TYPE
SYNTAX INTEGER (0..65535)
ACCESS read-only
STATUS optional
DESCRIPTION
        " "
::= { outlet32PDU11 4 }

pf32PDU11 OBJECT-TYPE
SYNTAX INTEGER (0..65535)
ACCESS read-only
STATUS optional
DESCRIPTION
        " "
::= { outlet32PDU11 5 }

energy32PDU11 OBJECT-TYPE
SYNTAX INTEGER (0..65535)
ACCESS read-only
STATUS optional
DESCRIPTION
        " "
::= { outlet32PDU11 6 }

switch33PDU11 OBJECT-TYPE
SYNTAX INTEGER (0..3)
ACCESS read-write
STATUS optional
DESCRIPTION
        " "
::= { outlet33PDU11 1 }

voltage33PDU11 OBJECT-TYPE
SYNTAX INTEGER (0..65535)
ACCESS read-only
STATUS optional
DESCRIPTION
        " "
::= { outlet33PDU11 2 }

current33PDU11 OBJECT-TYPE
SYNTAX INTEGER (0..65535)
ACCESS read-only
STATUS optional
DESCRIPTION
        " "
::= { outlet33PDU11 3 }

power33PDU11 OBJECT-TYPE
SYNTAX INTEGER (0..65535)
ACCESS read-only
STATUS optional
DESCRIPTION
        " "
::= { outlet33PDU11 4 }

pf33PDU11 OBJECT-TYPE
SYNTAX INTEGER (0..65535)
ACCESS read-only
STATUS optional
DESCRIPTION
        " "
::= { outlet33PDU11 5 }

energy33PDU11 OBJECT-TYPE
SYNTAX INTEGER (0..65535)
ACCESS read-only
STATUS optional
DESCRIPTION
        " "
::= { outlet33PDU11 6 }

switch34PDU11 OBJECT-TYPE
SYNTAX INTEGER (0..3)
ACCESS read-write
STATUS optional
DESCRIPTION
        " "
::= { outlet34PDU11 1 }

voltage34PDU11 OBJECT-TYPE
SYNTAX INTEGER (0..65535)
ACCESS read-only
STATUS optional
DESCRIPTION
        " "
::= { outlet34PDU11 2 }

current34PDU11 OBJECT-TYPE
SYNTAX INTEGER (0..65535)
ACCESS read-only
STATUS optional
DESCRIPTION
        " "
::= { outlet34PDU11 3 }

power34PDU11 OBJECT-TYPE
SYNTAX INTEGER (0..65535)
ACCESS read-only
STATUS optional
DESCRIPTION
        " "
::= { outlet34PDU11 4 }

pf34PDU11 OBJECT-TYPE
SYNTAX INTEGER (0..65535)
ACCESS read-only
STATUS optional
DESCRIPTION
        " "
::= { outlet34PDU11 5 }

energy34PDU11 OBJECT-TYPE
SYNTAX INTEGER (0..65535)
ACCESS read-only
STATUS optional
DESCRIPTION
        " "
::= { outlet34PDU11 6 }

switch35PDU11 OBJECT-TYPE
SYNTAX INTEGER (0..3)
ACCESS read-write
STATUS optional
DESCRIPTION
        " "
::= { outlet35PDU11 1 }

voltage35PDU11 OBJECT-TYPE
SYNTAX INTEGER (0..65535)
ACCESS read-only
STATUS optional
DESCRIPTION
        " "
::= { outlet35PDU11 2 }

current35PDU11 OBJECT-TYPE
SYNTAX INTEGER (0..65535)
ACCESS read-only
STATUS optional
DESCRIPTION
        " "
::= { outlet35PDU11 3 }

power35PDU11 OBJECT-TYPE
SYNTAX INTEGER (0..65535)
ACCESS read-only
STATUS optional
DESCRIPTION
        " "
::= { outlet35PDU11 4 }

pf35PDU11 OBJECT-TYPE
SYNTAX INTEGER (0..65535)
ACCESS read-only
STATUS optional
DESCRIPTION
        " "
::= { outlet35PDU11 5 }

energy35PDU11 OBJECT-TYPE
SYNTAX INTEGER (0..65535)
ACCESS read-only
STATUS optional
DESCRIPTION
        " "
::= { outlet35PDU11 6 }

switch36PDU11 OBJECT-TYPE
SYNTAX INTEGER (0..3)
ACCESS read-write
STATUS optional
DESCRIPTION
        " "
::= { outlet36PDU11 1 }

voltage36PDU11 OBJECT-TYPE
SYNTAX INTEGER (0..65535)
ACCESS read-only
STATUS optional
DESCRIPTION
        " "
::= { outlet36PDU11 2 }

current36PDU11 OBJECT-TYPE
SYNTAX INTEGER (0..65535)
ACCESS read-only
STATUS optional
DESCRIPTION
        " "
::= { outlet36PDU11 3 }

power36PDU11 OBJECT-TYPE
SYNTAX INTEGER (0..65535)
ACCESS read-only
STATUS optional
DESCRIPTION
        " "
::= { outlet36PDU11 4 }

pf36PDU11 OBJECT-TYPE
SYNTAX INTEGER (0..65535)
ACCESS read-only
STATUS optional
DESCRIPTION
        " "
::= { outlet36PDU11 5 }

energy36PDU11 OBJECT-TYPE
SYNTAX INTEGER (0..65535)
ACCESS read-only
STATUS optional
DESCRIPTION
        " "
::= { outlet36PDU11 6 }

sensor1 OBJECT IDENTIFIER ::= { pdu11 4 }

temperature1PDU11 OBJECT-TYPE
SYNTAX INTEGER (0..65535)
ACCESS read-only
STATUS optional
DESCRIPTION
        " "
::= { sensor1 1 }

humidity1PDU11 OBJECT-TYPE
SYNTAX INTEGER (0..65535)
ACCESS read-only
STATUS optional
DESCRIPTION
        " "
::= { sensor1 2 }

temperature2PDU11 OBJECT-TYPE
SYNTAX INTEGER (0..65535)
ACCESS read-only
STATUS optional
DESCRIPTION
        " "
::= { sensor1 3 }

humidity2PDU11 OBJECT-TYPE
SYNTAX INTEGER (0..65535)
ACCESS read-only
STATUS optional
DESCRIPTION
        " "
::= { sensor1 4 }

inputStatus1PDU11 OBJECT-TYPE
SYNTAX INTEGER (0..1)
ACCESS read-only
STATUS optional
DESCRIPTION
        " "
::= { sensor1 5 }

inputStatus2PDU11 OBJECT-TYPE
SYNTAX INTEGER (0..1)
ACCESS read-only
STATUS optional
DESCRIPTION
        " "
::= { sensor1 6 }

inputStatus3PDU11 OBJECT-TYPE
SYNTAX INTEGER (0..1)
ACCESS read-only
STATUS optional
DESCRIPTION
        " "
::= { sensor1 7 }

inputStatus4PDU11 OBJECT-TYPE
SYNTAX INTEGER (0..1)
ACCESS read-only
STATUS optional
DESCRIPTION
        " "
::= { sensor1 8 }

doStatus1PDU11 OBJECT-TYPE
SYNTAX INTEGER (0..1)
ACCESS read-only
STATUS optional
DESCRIPTION
        " "
::= { sensor1 9 }

doStatus2PDU11 OBJECT-TYPE
SYNTAX INTEGER (0..1)
ACCESS read-only
STATUS optional
DESCRIPTION
        " "
::= { sensor1 10 }

END
